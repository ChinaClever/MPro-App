ZPDU DEFINITIONS ::= BEGIN

IMPORTS

DisplayString                                                   FROM SNMPv2-TC
MODULE-IDENTITY, OBJECT-TYPE,enterprises,Integer32,NOTIFICATION-TYPE FROM SNMPv2-SMI;

ZPDU MODULE-IDENTITY
	LAST-UPDATED "20180323SG"
	ORGANIZATION "xxx"
	CONTACT-INFO "xxx"
	DESCRIPTION "MIB for ZPDU Products"
	::= {enterprises 30966 }


PDUSys OBJECT IDENTIFIER ::= { enterprises 30966 }
pdu OBJECT IDENTIFIER ::= { PDUSys 7}  


-------------------------------master information--------------------
master OBJECT IDENTIFIER ::= { pdu 1}
masterInformation OBJECT IDENTIFIER ::= { master 1}
masterName OBJECT-TYPE
    SYNTAX      DisplayString
    MAX-ACCESS  read-write
    STATUS      current
    DESCRIPTION
	"This is the first device."
    ::= { masterInformation 1}
    
masterType OBJECT-TYPE
    SYNTAX      DisplayString
    MAX-ACCESS  read-only
    STATUS      current
    DESCRIPTION
	"This is device type "
    ::= { masterInformation 2}
    
masterOutputNumber OBJECT-TYPE 
    SYNTAX      Integer32
    MAX-ACCESS  read-only
    STATUS      current
    DESCRIPTION
	"This is the number of output bits"
	::= { masterInformation 3}
	
masterMacAdress OBJECT-TYPE
    SYNTAX      DisplayString
    MAX-ACCESS  read-only
    STATUS      current
    DESCRIPTION
	"This is device MAC adress"
    ::= { masterInformation 4}	

masterVison OBJECT-TYPE
    SYNTAX      DisplayString
    MAX-ACCESS  read-only
    STATUS      current
    DESCRIPTION
	"This is device vison "
    ::= { masterInformation 5}

masterFrequency OBJECT-TYPE
    SYNTAX      Integer32
    MAX-ACCESS  read-only
    STATUS      current
    DESCRIPTION
	"This is device frequency "
    ::= { masterInformation 6}
	
masterEmission OBJECT-TYPE
    SYNTAX      DisplayString
    MAX-ACCESS  read-only
    STATUS      current
    DESCRIPTION
	"This is device emission "
    ::= { masterInformation 7}	
	
masterRunTime OBJECT-TYPE
    SYNTAX      DisplayString
    MAX-ACCESS  read-only
    STATUS      current
    DESCRIPTION
	"This is device running time "
    ::= { masterInformation 8}	

masterBuzzerSwitch OBJECT-TYPE
    SYNTAX      DisplayString
    MAX-ACCESS  read-write
    STATUS      current
    DESCRIPTION
	"This is device buzzer switch."
    ::= { masterInformation 9}	

	
-------------------------------master phase--------------------
masterPhase OBJECT IDENTIFIER ::= { master 2}	
	
masterPhaseOne OBJECT IDENTIFIER ::= { masterPhase 1}	    
masterPhaseOneCurrent OBJECT-TYPE
    SYNTAX      DisplayString
    MAX-ACCESS  read-only
    STATUS      current
    DESCRIPTION
	"The current of phase one"
    ::= { masterPhaseOne 1}

masterPhaseOneVoltage OBJECT-TYPE
    SYNTAX      DisplayString
    MAX-ACCESS  read-only
    STATUS      current
    DESCRIPTION
	"The voltage of phase one"
    ::= { masterPhaseOne 2}

masterPhaseOnePower OBJECT-TYPE
    SYNTAX      DisplayString
    MAX-ACCESS  read-only
    STATUS      current
    DESCRIPTION
	"The power of phase one"
    ::= { masterPhaseOne 3}
	
masterPhaseOnePowerfactor OBJECT-TYPE
    SYNTAX      DisplayString
    MAX-ACCESS  read-only
    STATUS      current
    DESCRIPTION
	"The power factor of phase one"
    ::= { masterPhaseOne 4}	
	
masterPhaseOneEnergy OBJECT-TYPE
    SYNTAX      DisplayString
    MAX-ACCESS  read-only
    STATUS      current
    DESCRIPTION
	"The energy of phase one"
    ::= { masterPhaseOne 5}	
		
masterPhaseOneCurrentMin OBJECT-TYPE
    SYNTAX      DisplayString
    MAX-ACCESS  read-write
    STATUS      current
    DESCRIPTION
	"The min current of phase one"
    ::= { masterPhaseOne 6}	
	
masterPhaseOneCurrentMinCritical OBJECT-TYPE
    SYNTAX      DisplayString
    MAX-ACCESS  read-write
    STATUS      current
    DESCRIPTION
	"The min critical current of phase one"
    ::= { masterPhaseOne 7}
	
masterPhaseOneCurrentMaxCritical OBJECT-TYPE
    SYNTAX      DisplayString
    MAX-ACCESS  read-write
    STATUS      current
    DESCRIPTION
	"The max critical current of phase one"
    ::= { masterPhaseOne 8}
	
masterPhaseOneCurrentMax OBJECT-TYPE
    SYNTAX      DisplayString
    MAX-ACCESS  read-write
    STATUS      current
    DESCRIPTION
	"The max current of phase one"
    ::= { masterPhaseOne 9}
	
masterPhaseOneVoltageMin OBJECT-TYPE
    SYNTAX      DisplayString
    MAX-ACCESS  read-write
    STATUS      current
    DESCRIPTION
	"The min voltage of phase one"
    ::= { masterPhaseOne 10}
	
masterPhaseOneVoltageMinCritical OBJECT-TYPE
    SYNTAX      DisplayString
    MAX-ACCESS  read-write
    STATUS      current
    DESCRIPTION
	"The min critical voltage of phase one"
    ::= { masterPhaseOne 11}

masterPhaseOneVoltageMaxCritical OBJECT-TYPE
    SYNTAX      DisplayString
    MAX-ACCESS  read-write
    STATUS      current
    DESCRIPTION
	"The max critical of phase one"
    ::= { masterPhaseOne 12}
	
masterPhaseOneVoltageMax OBJECT-TYPE
    SYNTAX      DisplayString
    MAX-ACCESS  read-write
    STATUS      current
    DESCRIPTION
	"The max voltage of phase one"
    ::= { masterPhaseOne 13}


masterPhaseTwo OBJECT IDENTIFIER ::= { masterPhase 2}	    
masterPhaseTwoCurrent OBJECT-TYPE
    SYNTAX      DisplayString
    MAX-ACCESS  read-only
    STATUS      current
    DESCRIPTION
	"The current of phase two"
    ::= { masterPhaseTwo 1}

masterPhaseTwoVoltage OBJECT-TYPE
    SYNTAX      DisplayString
    MAX-ACCESS  read-only
    STATUS      current
    DESCRIPTION
	"The voltage of phase two"
    ::= { masterPhaseTwo 2}

masterPhaseTwoPower OBJECT-TYPE
    SYNTAX      DisplayString
    MAX-ACCESS  read-only
    STATUS      current
    DESCRIPTION
	"The power of phase two"
    ::= { masterPhaseTwo 3}
	
masterPhaseTwoPowerfactor OBJECT-TYPE
    SYNTAX      DisplayString
    MAX-ACCESS  read-only
    STATUS      current
    DESCRIPTION
	"The power factor of phase two"
    ::= { masterPhaseTwo 4}	
	
masterPhaseTwoEnergy OBJECT-TYPE
    SYNTAX      DisplayString
    MAX-ACCESS  read-only
    STATUS      current
    DESCRIPTION
	"The energy of phase two"
    ::= { masterPhaseTwo 5}	
		
masterPhaseTwoCurrentMin OBJECT-TYPE
    SYNTAX      DisplayString
    MAX-ACCESS  read-write
    STATUS      current
    DESCRIPTION
	"The min current of phase two"
    ::= { masterPhaseTwo 6}	
	
masterPhaseTwoCurrentMinCritical OBJECT-TYPE
    SYNTAX      DisplayString
    MAX-ACCESS  read-write
    STATUS      current
    DESCRIPTION
	"The min critical current of phase two"
    ::= { masterPhaseTwo 7}
	
masterPhaseTwoCurrentMaxCritical OBJECT-TYPE
    SYNTAX      DisplayString
    MAX-ACCESS  read-write
    STATUS      current
    DESCRIPTION
	"The max critical current of phase two"
    ::= { masterPhaseTwo 8}
	
masterPhaseTwoCurrentMax OBJECT-TYPE
    SYNTAX      DisplayString
    MAX-ACCESS  read-write
    STATUS      current
    DESCRIPTION
	"The max current of phase two"
    ::= { masterPhaseTwo 9}
	
masterPhaseTwoVoltageMin OBJECT-TYPE
    SYNTAX      DisplayString
    MAX-ACCESS  read-write
    STATUS      current
    DESCRIPTION
	"The min voltage of phase two"
    ::= { masterPhaseTwo 10}
	
masterPhaseTwoVoltageMinCritical OBJECT-TYPE
    SYNTAX      DisplayString
    MAX-ACCESS  read-write
    STATUS      current
    DESCRIPTION
	"The min critical voltage of phase two"
    ::= { masterPhaseTwo 11}

masterPhaseTwoVoltageMaxCritical OBJECT-TYPE
    SYNTAX      DisplayString
    MAX-ACCESS  read-write
    STATUS      current
    DESCRIPTION
	"The max critical voltage of phase two"
    ::= { masterPhaseTwo 12}
	
masterPhaseTwoVoltageMax OBJECT-TYPE
    SYNTAX      DisplayString
    MAX-ACCESS  read-write
    STATUS      current
    DESCRIPTION
	"The max voltage of phase two"
    ::= { masterPhaseTwo 13}
	
	
masterPhaseThree OBJECT IDENTIFIER ::= { masterPhase 3}	    
masterPhaseThreeCurrent OBJECT-TYPE
    SYNTAX      DisplayString
    MAX-ACCESS  read-only
    STATUS      current
    DESCRIPTION
	"The current of phase three"
    ::= { masterPhaseThree 1}

masterPhaseThreeVoltage OBJECT-TYPE
    SYNTAX      DisplayString
    MAX-ACCESS  read-only
    STATUS      current
    DESCRIPTION
	"The voltage phase three"
    ::= { masterPhaseThree 2}

masterPhaseThreePower OBJECT-TYPE
    SYNTAX      DisplayString
    MAX-ACCESS  read-only
    STATUS      current
    DESCRIPTION
	"The power of phase three"
    ::= { masterPhaseThree 3}
	
masterPhaseThreePowerfactor OBJECT-TYPE
    SYNTAX      DisplayString
    MAX-ACCESS  read-only
    STATUS      current
    DESCRIPTION
	"The power factor of phase three"
    ::= { masterPhaseThree 4}	
	
masterPhaseThreeEnergy OBJECT-TYPE
    SYNTAX      DisplayString
    MAX-ACCESS  read-only
    STATUS      current
    DESCRIPTION
	"The energy of phase three"
    ::= { masterPhaseThree 5}	
		
masterPhaseThreeCurrentMin OBJECT-TYPE
    SYNTAX      DisplayString
    MAX-ACCESS  read-write
    STATUS      current
    DESCRIPTION
	"The min current of phase three"
    ::= { masterPhaseThree 6}	
	
masterPhaseThreeCurrentMinCritical OBJECT-TYPE
    SYNTAX      DisplayString
    MAX-ACCESS  read-write
    STATUS      current
    DESCRIPTION
	"The min critical current of phase three"
    ::= { masterPhaseThree 7}
	
masterPhaseThreeCurrentMaxCritical OBJECT-TYPE
    SYNTAX      DisplayString
    MAX-ACCESS  read-write
    STATUS      current
    DESCRIPTION
	"The max critical current of phase three"
    ::= { masterPhaseThree 8}
	
masterPhaseThreeCurrentMax OBJECT-TYPE
    SYNTAX      DisplayString
    MAX-ACCESS  read-write
    STATUS      current
    DESCRIPTION
	"The max current of phase three"
    ::= { masterPhaseThree 9}
	
masterPhaseThreeVoltageMin OBJECT-TYPE
    SYNTAX      DisplayString
    MAX-ACCESS  read-write
    STATUS      current
    DESCRIPTION
	"The min voltage of phase three"
    ::= { masterPhaseThree 10}
	
masterPhaseThreeVoltageMinCritical OBJECT-TYPE
    SYNTAX      DisplayString
    MAX-ACCESS  read-write
    STATUS      current
    DESCRIPTION
	"The min critical voltage of phase three"
    ::= { masterPhaseThree 11}

masterPhaseThreeVoltageMaxCritical OBJECT-TYPE
    SYNTAX      DisplayString
    MAX-ACCESS  read-write
    STATUS      current
    DESCRIPTION
	"The max critical voltage of phase three"
    ::= { masterPhaseThree 12}
	
masterPhaseThreeVoltageMax OBJECT-TYPE
    SYNTAX      DisplayString
    MAX-ACCESS  read-write
    STATUS      current
    DESCRIPTION
	"The max voltage of phase three"
    ::= { masterPhaseThree 13}
	
	
-------------------------------master circuit--------------------	
masterCircuit OBJECT IDENTIFIER ::= { master 3}	

masterCircuitOne OBJECT IDENTIFIER ::= { masterCircuit 1}	    
masterCircuitOneBreaker OBJECT-TYPE
    SYNTAX      DisplayString
    MAX-ACCESS  read-only
    STATUS      current
    DESCRIPTION
	"The circuit one breaker"
    ::= { masterCircuitOne 1}
	
masterCircuitOneManagementBit OBJECT-TYPE
    SYNTAX      DisplayString
    MAX-ACCESS  read-only
    STATUS      current
    DESCRIPTION
	"The managerment bits of circuit one"
    ::= { masterCircuitOne 2}	

masterCircuitOneCurrent OBJECT-TYPE
    SYNTAX      DisplayString
    MAX-ACCESS  read-only
    STATUS      current
    DESCRIPTION
	"The current of circuit one"
    ::= { masterCircuitOne 3}

masterCircuitOneVoltage OBJECT-TYPE
    SYNTAX      DisplayString
    MAX-ACCESS  read-only
    STATUS      current
    DESCRIPTION
	"The voltage of circuit one"
    ::= { masterCircuitOne 4}

masterCircuitOneEnergy OBJECT-TYPE
    SYNTAX      DisplayString
    MAX-ACCESS  read-only
    STATUS      current
    DESCRIPTION
	"The energy of circuit one"
    ::= { masterCircuitOne 5}	
	
masterCircuitOnePower OBJECT-TYPE
    SYNTAX      DisplayString
    MAX-ACCESS  read-only
    STATUS      current
    DESCRIPTION
	"The power of circuit one "
    ::= { masterCircuitOne 6}
	
masterCircuitOneCurrentMin OBJECT-TYPE
    SYNTAX      DisplayString
    MAX-ACCESS  read-write
    STATUS      current
    DESCRIPTION
	"The min current of circuit one "
    ::= { masterCircuitOne 7}	
	
masterCircuitOneCurrentMinCritical OBJECT-TYPE
    SYNTAX      DisplayString
    MAX-ACCESS  read-write
    STATUS      current
    DESCRIPTION
	"The min critical current of circuit one"
    ::= { masterCircuitOne 8}
	
masterCircuitOneCurrentMaxCritical OBJECT-TYPE
    SYNTAX      DisplayString
    MAX-ACCESS  read-write
    STATUS      current
    DESCRIPTION
	"The max critical current of circuit one "
    ::= { masterCircuitOne 9}
	
masterCircuitOneCurrentMax OBJECT-TYPE
    SYNTAX      DisplayString
    MAX-ACCESS  read-write
    STATUS      current
    DESCRIPTION
	"The max current of circuit one"
    ::= { masterCircuitOne 10}
	

masterCircuitTwo OBJECT IDENTIFIER ::= { masterCircuit 2}	    
masterCircuitTwoBreaker OBJECT-TYPE
    SYNTAX      DisplayString
    MAX-ACCESS  read-only
    STATUS      current
    DESCRIPTION
	"The circuit breaker two"
    ::= { masterCircuitTwo 1}
	
masterCircuitTwoManagementBit OBJECT-TYPE
    SYNTAX      DisplayString
    MAX-ACCESS  read-only
    STATUS      current
    DESCRIPTION
	"The managerment bits of circuit two"
    ::= { masterCircuitTwo 2}	

masterCircuitTwoCurrent OBJECT-TYPE
    SYNTAX      DisplayString
    MAX-ACCESS  read-only
    STATUS      current
    DESCRIPTION
	"The current of circuit two"
    ::= { masterCircuitTwo 3}

masterCircuitTwoVoltage OBJECT-TYPE
    SYNTAX      DisplayString
    MAX-ACCESS  read-only
    STATUS      current
    DESCRIPTION
	"The voltage of circuit two"
    ::= { masterCircuitTwo 4}

masterCircuitTwoEnergy OBJECT-TYPE
    SYNTAX      DisplayString
    MAX-ACCESS  read-only
    STATUS      current
    DESCRIPTION
	"The energy of circuit two"
    ::= { masterCircuitTwo 5}	
	
masterCircuitTwoPower OBJECT-TYPE
    SYNTAX      DisplayString
    MAX-ACCESS  read-only
    STATUS      current
    DESCRIPTION
	"The power of circuit two"
    ::= { masterCircuitTwo 6}
	
masterCircuitTwoCurrentMin OBJECT-TYPE
    SYNTAX      DisplayString
    MAX-ACCESS  read-write
    STATUS      current
    DESCRIPTION
	"The min current of circuit two"
    ::= { masterCircuitTwo 7}	
	
masterCircuitTwoCurrentMinCritical OBJECT-TYPE
    SYNTAX      DisplayString
    MAX-ACCESS  read-write
    STATUS      current
    DESCRIPTION
	"The min critical current of circuit two"
    ::= { masterCircuitTwo 8}
	
masterCircuitTwoCurrentMaxCritical OBJECT-TYPE
    SYNTAX      DisplayString
    MAX-ACCESS  read-write
    STATUS      current
    DESCRIPTION
	"The max critical current of phase two"
    ::= { masterCircuitTwo 9}
	
masterCircuitTwoCurrentMax OBJECT-TYPE
    SYNTAX      DisplayString
    MAX-ACCESS  read-write
    STATUS      current
    DESCRIPTION
	"The max current of circuit two"
    ::= { masterCircuitTwo 10}
	
	
masterCircuitThree OBJECT IDENTIFIER ::= { masterCircuit 3}	    
masterCircuitThreeBreaker OBJECT-TYPE
    SYNTAX      DisplayString
    MAX-ACCESS  read-only
    STATUS      current
    DESCRIPTION
	"The circuit breaker three"
    ::= { masterCircuitThree 1}
	
masterCircuitThreeManagementBit OBJECT-TYPE
    SYNTAX      DisplayString
    MAX-ACCESS  read-only
    STATUS      current
    DESCRIPTION
	"The managerment bits of circuit three"
    ::= { masterCircuitThree 2}	

masterCircuitThreeCurrent OBJECT-TYPE
    SYNTAX      DisplayString
    MAX-ACCESS  read-only
    STATUS      current
    DESCRIPTION
	"The current of circuit three"
    ::= { masterCircuitThree 3}

masterCircuitThreeVoltage OBJECT-TYPE
    SYNTAX      DisplayString
    MAX-ACCESS  read-only
    STATUS      current
    DESCRIPTION
	"The voltage of circuit three"
    ::= { masterCircuitThree 4}

masterCircuitThreeEnergy OBJECT-TYPE
    SYNTAX      DisplayString
    MAX-ACCESS  read-only
    STATUS      current
    DESCRIPTION
	"The energy of circuit three"
    ::= { masterCircuitThree 5}	
	
masterCircuitThreePower OBJECT-TYPE
    SYNTAX      DisplayString
    MAX-ACCESS  read-only
    STATUS      current
    DESCRIPTION
	"The power of circuit three"
    ::= { masterCircuitThree 6}
	
masterCircuitThreeCurrentMin OBJECT-TYPE
    SYNTAX      DisplayString
    MAX-ACCESS  read-write
    STATUS      current
    DESCRIPTION
	"The min current of circuit three"
    ::= { masterCircuitThree 7}	
	
masterCircuitThreeCurrentMinCritical OBJECT-TYPE
    SYNTAX      DisplayString
    MAX-ACCESS  read-write
    STATUS      current
    DESCRIPTION
	"The min critical current of circuit three"
    ::= { masterCircuitThree 8}
	
masterCircuitThreeCurrentMaxCritical OBJECT-TYPE
    SYNTAX      DisplayString
    MAX-ACCESS  read-write
    STATUS      current
    DESCRIPTION
	"The max critical current of circuit three"
    ::= { masterCircuitThree 9}
	
masterCircuitThreeCurrentMax OBJECT-TYPE
    SYNTAX      DisplayString
    MAX-ACCESS  read-write
    STATUS      current
    DESCRIPTION
	"The max current of circuit three"
    ::= { masterCircuitThree 10}
	
	
masterCircuitFour OBJECT IDENTIFIER ::= { masterCircuit 4}	    
masterCircuitFourBreaker OBJECT-TYPE
    SYNTAX      DisplayString
    MAX-ACCESS  read-only
    STATUS      current
    DESCRIPTION
	"The circuit four breaker"
    ::= { masterCircuitFour 1}
	
masterCircuitFourManagementBit OBJECT-TYPE
    SYNTAX      DisplayString
    MAX-ACCESS  read-only
    STATUS      current
    DESCRIPTION
	"The managerment bits of circuit four"
    ::= { masterCircuitFour 2}	

masterCircuitFourCurrent OBJECT-TYPE
    SYNTAX      DisplayString
    MAX-ACCESS  read-only
    STATUS      current
    DESCRIPTION
	"The current of circuit four"
    ::= { masterCircuitFour 3}

masterCircuitFourVoltage OBJECT-TYPE
    SYNTAX      DisplayString
    MAX-ACCESS  read-only
    STATUS      current
    DESCRIPTION
	"The voltage of circuit four"
    ::= { masterCircuitFour 4}

masterCircuitFourEnergy OBJECT-TYPE
    SYNTAX      DisplayString
    MAX-ACCESS  read-only
    STATUS      current
    DESCRIPTION
	"The energy of circuit four"
    ::= { masterCircuitFour 5}	
	
masterCircuitFourPower OBJECT-TYPE
    SYNTAX      DisplayString
    MAX-ACCESS  read-only
    STATUS      current
    DESCRIPTION
	"The power of circuit four"
    ::= { masterCircuitFour 6}
	
masterCircuitFourCurrentMin OBJECT-TYPE
    SYNTAX      DisplayString
    MAX-ACCESS  read-write
    STATUS      current
    DESCRIPTION
	"The min current of circuit four"
    ::= { masterCircuitFour 7}	
	
masterCircuitFourCurrentMinCritical OBJECT-TYPE
    SYNTAX      DisplayString
    MAX-ACCESS  read-write
    STATUS      current
    DESCRIPTION
	"The min critical current of circuit four"
    ::= { masterCircuitFour 8}
	
masterCircuitFourCurrentMaxCritical OBJECT-TYPE
    SYNTAX      DisplayString
    MAX-ACCESS  read-write
    STATUS      current
    DESCRIPTION
	"The max critical current of circuit four"
    ::= { masterCircuitFour 9}
	
masterCircuitFourCurrentMax OBJECT-TYPE
    SYNTAX      DisplayString
    MAX-ACCESS  read-write
    STATUS      current
    DESCRIPTION
	"The power of phase one"
    ::= { masterCircuitFour 10}
	
	
masterCircuitFive OBJECT IDENTIFIER ::= { masterCircuit 5}	    
masterCircuitFiveBreaker OBJECT-TYPE
    SYNTAX      DisplayString
    MAX-ACCESS  read-only
    STATUS      current
    DESCRIPTION
	"The circuit five breaker"
    ::= { masterCircuitFive 1}
	
masterCircuitFiveManagementBit OBJECT-TYPE
    SYNTAX      DisplayString
    MAX-ACCESS  read-only
    STATUS      current
    DESCRIPTION
	"The managerment bits of circuit five"
    ::= { masterCircuitFive 2}	

masterCircuitFiveCurrent OBJECT-TYPE
    SYNTAX      DisplayString
    MAX-ACCESS  read-only
    STATUS      current
    DESCRIPTION
	"The current of circuit five"
    ::= { masterCircuitFive 3}

masterCircuitFiveVoltage OBJECT-TYPE
    SYNTAX      DisplayString
    MAX-ACCESS  read-only
    STATUS      current
    DESCRIPTION
	"The voltage of circuit five"
    ::= { masterCircuitFive 4}

masterCircuitFiveEnergy OBJECT-TYPE
    SYNTAX      DisplayString
    MAX-ACCESS  read-only
    STATUS      current
    DESCRIPTION
	"The energy of circuit five"
    ::= { masterCircuitFive 5}	
	
masterCircuitFivePower OBJECT-TYPE
    SYNTAX      DisplayString
    MAX-ACCESS  read-only
    STATUS      current
    DESCRIPTION
	"The power of circuit five"
    ::= { masterCircuitFive 6}
		
masterCircuitFiveCurrentMin OBJECT-TYPE
    SYNTAX      DisplayString
    MAX-ACCESS  read-write
    STATUS      current
    DESCRIPTION
	"The min current of circuit five"
    ::= { masterCircuitFive 7}	
	
masterCircuitFiveCurrentMinCritical OBJECT-TYPE
    SYNTAX      DisplayString
    MAX-ACCESS  read-write
    STATUS      current
    DESCRIPTION
	"The min critical current of circuit five"
    ::= { masterCircuitFive 8}
	
masterCircuitFiveCurrentMaxCritical OBJECT-TYPE
    SYNTAX      DisplayString
    MAX-ACCESS  read-write
    STATUS      current
    DESCRIPTION
	"The max critical of circuit five"
    ::= { masterCircuitFive 9}
	
masterCircuitFiveCurrentMax OBJECT-TYPE
    SYNTAX      DisplayString
    MAX-ACCESS  read-write
    STATUS      current
    DESCRIPTION
	"The max current of circuit five"
    ::= { masterCircuitFive 10}

	
masterCircuitSix OBJECT IDENTIFIER ::= { masterCircuit 6}	    
masterCircuitSixBreaker OBJECT-TYPE
    SYNTAX      DisplayString
    MAX-ACCESS  read-only
    STATUS      current
    DESCRIPTION
	"The circuit six breaker"
    ::= { masterCircuitSix 1}
	
masterCircuitSixManagementBit OBJECT-TYPE
    SYNTAX      DisplayString
    MAX-ACCESS  read-only
    STATUS      current
    DESCRIPTION
	"The managerment bits of circuit six"
    ::= { masterCircuitSix 2}	

masterCircuitSixCurrent OBJECT-TYPE
    SYNTAX      DisplayString
    MAX-ACCESS  read-only
    STATUS      current
    DESCRIPTION
	"The current of circuit six"
    ::= { masterCircuitSix 3}

masterCircuitSixVoltage OBJECT-TYPE
    SYNTAX      DisplayString
    MAX-ACCESS  read-only
    STATUS      current
    DESCRIPTION
	"The voltage of circuit six"
    ::= { masterCircuitSix 4}

masterCircuitSixEnergy OBJECT-TYPE
    SYNTAX      DisplayString
    MAX-ACCESS  read-only
    STATUS      current
    DESCRIPTION
	"The energy of circuit six"
    ::= { masterCircuitSix 5}	
	
masterCircuitSixPower OBJECT-TYPE
    SYNTAX      DisplayString
    MAX-ACCESS  read-only
    STATUS      current
    DESCRIPTION
	"The power of circuit six"
    ::= { masterCircuitSix 6}
	
masterCircuitSixCurrentMin OBJECT-TYPE
    SYNTAX      DisplayString
    MAX-ACCESS  read-write
    STATUS      current
    DESCRIPTION
	"The min current of circuit six"
    ::= { masterCircuitSix 7}	
	
masterCircuitSixCurrentMinCritical OBJECT-TYPE
    SYNTAX      DisplayString
    MAX-ACCESS  read-write
    STATUS      current
    DESCRIPTION
	"The min critical current of circuit six"
    ::= { masterCircuitSix 8}
	
masterCircuitSixCurrentMaxCritical OBJECT-TYPE
    SYNTAX      DisplayString
    MAX-ACCESS  read-write
    STATUS      current
    DESCRIPTION
	"The max critical current of circuit six"
    ::= { masterCircuitSix 9}
	
masterCircuitSixCurrentMax OBJECT-TYPE
    SYNTAX      DisplayString
    MAX-ACCESS  read-write
    STATUS      current
    DESCRIPTION
	"The max current of circuit six"
    ::= { masterCircuitSix 10}

	
-------------------------------master sensor------------------------	
masterSensor OBJECT IDENTIFIER ::= { master 4}
masterSensorTemperatureOne OBJECT-TYPE
    SYNTAX      DisplayString
    MAX-ACCESS  read-only
    STATUS      current
    DESCRIPTION
	"This is the temperature of sensor one."
    ::= { masterSensor 1}
	
masterSensorTemperatureTwo OBJECT-TYPE
    SYNTAX      DisplayString
    MAX-ACCESS  read-only
    STATUS      current
    DESCRIPTION
	"This is the temperature of sensor two."
    ::= { masterSensor 2}

masterSensorHumidityOne OBJECT-TYPE
    SYNTAX      DisplayString
    MAX-ACCESS  read-only
    STATUS      current
    DESCRIPTION
	"This is the humidity of sensor one."
    ::= { masterSensor 3}

masterSensorHumidityTwo OBJECT-TYPE
    SYNTAX      DisplayString
    MAX-ACCESS  read-only
    STATUS      current
    DESCRIPTION
	"This is the humidity of sensor two."
    ::= { masterSensor 4}	

masterSensorDoorOne OBJECT-TYPE
    SYNTAX      DisplayString
    MAX-ACCESS  read-only
    STATUS      current
    DESCRIPTION
	"The door sensor one"
    ::= { masterSensor 5}

masterSensorDoorTwo OBJECT-TYPE
    SYNTAX      DisplayString
    MAX-ACCESS  read-only
    STATUS      current
    DESCRIPTION
	"The door sensor two"
    ::= { masterSensor 6}	
	
masterSensorSmoke OBJECT-TYPE
    SYNTAX      DisplayString
    MAX-ACCESS  read-only
    STATUS      current
    DESCRIPTION
	"The smoke sensor"
    ::= { masterSensor 7}
	
masterSensorWater OBJECT-TYPE
    SYNTAX      DisplayString
    MAX-ACCESS  read-only
    STATUS      current
    DESCRIPTION
	"The water sensor"
    ::= { masterSensor 8}
	
masterSensorTemperatureOneMin OBJECT-TYPE
    SYNTAX      DisplayString
    MAX-ACCESS  read-write
    STATUS      current
    DESCRIPTION
	"This is the min temperature of sensor one."
    ::= { masterSensor 9}
	
masterSensorTemperatureOneMinCritical OBJECT-TYPE
    SYNTAX      DisplayString
    MAX-ACCESS  read-write
    STATUS      current
    DESCRIPTION
	"This is the min critical temperature of sensor one."
    ::= { masterSensor 10}	
	
masterSensorTemperatureOneMaxCritical OBJECT-TYPE
    SYNTAX      DisplayString
    MAX-ACCESS  read-write
    STATUS      current
    DESCRIPTION
	"This is the max critical temperature of sensor one."
    ::= { masterSensor 11}
	
masterSensorTemperatureOneMax OBJECT-TYPE
    SYNTAX      DisplayString
    MAX-ACCESS  read-write
    STATUS      current
    DESCRIPTION
	"This is the max temperature of sensor one."
    ::= { masterSensor 12}

masterSensorTemperatureTwoMin OBJECT-TYPE
    SYNTAX      DisplayString
    MAX-ACCESS  read-write
    STATUS      current
    DESCRIPTION
	"This is the temperature of sensor two."
    ::= { masterSensor 13}
	
masterSensorTemperatureTwoMinCritical OBJECT-TYPE
    SYNTAX      DisplayString
    MAX-ACCESS  read-write
    STATUS      current
    DESCRIPTION
	"This is the min critical temperature of sensor two."
    ::= { masterSensor 14}	
	
masterSensorTemperatureTwoMaxCritical OBJECT-TYPE
    SYNTAX      DisplayString
    MAX-ACCESS  read-write
    STATUS      current
    DESCRIPTION
	"This is the max critical temperature of sensor two."
    ::= { masterSensor 15}
	
masterSensorTemperatureTwoMax OBJECT-TYPE
    SYNTAX      DisplayString
    MAX-ACCESS  read-write
    STATUS      current
    DESCRIPTION
	"This is the max temperature of sensor two."
    ::= { masterSensor 16}
	
masterSensorHumidityOneMin OBJECT-TYPE
    SYNTAX      DisplayString
    MAX-ACCESS  read-write
    STATUS      current
    DESCRIPTION
	"This is the min humidity of sensor one."
    ::= { masterSensor 17}
	
masterSensorHumidityOneMinCritical OBJECT-TYPE
    SYNTAX      DisplayString
    MAX-ACCESS  read-write
    STATUS      current
    DESCRIPTION
	"This is the min critical humidity of sensor one."
    ::= { masterSensor 18}	
	
masterSensorHumidityOneMaxCritical OBJECT-TYPE
    SYNTAX      DisplayString
    MAX-ACCESS  read-write
    STATUS      current
    DESCRIPTION
	"This is the max critical humidity of sensor one."
    ::= { masterSensor 19}
	
masterSensorHumidityOneMax OBJECT-TYPE
    SYNTAX      DisplayString
    MAX-ACCESS  read-write
    STATUS      current
    DESCRIPTION
	"This is the max humidity of sensor one."
    ::= { masterSensor 20}

masterSensorHumidityTwoMin OBJECT-TYPE
    SYNTAX      DisplayString
    MAX-ACCESS  read-write
    STATUS      current
    DESCRIPTION
	"This is the min humidity of sensor two."
    ::= { masterSensor 21}
	
masterSensorHumidityTwoMinCritical OBJECT-TYPE
    SYNTAX      DisplayString
    MAX-ACCESS  read-write
    STATUS      current
    DESCRIPTION
	"This is the min critical humidity of sensor two."
    ::= { masterSensor 22}	
	
masterSensorHumidityTwoMaxCritical OBJECT-TYPE
    SYNTAX      DisplayString
    MAX-ACCESS  read-write
    STATUS      current
    DESCRIPTION
	"This is the max critical humidity of sensor two."
    ::= { masterSensor 23}
	
masterSensorHumidityTwoMax OBJECT-TYPE
    SYNTAX      DisplayString
    MAX-ACCESS  read-write
    STATUS      current
    DESCRIPTION
	"This is the max humidity of sensor two."
    ::= { masterSensor 24}
	
-------------------------------master output name------------------------	
masterOutputName OBJECT IDENTIFIER ::= { master 5}
masterOutputNameOne OBJECT-TYPE
    SYNTAX      DisplayString
    MAX-ACCESS  read-write
    STATUS      current
    DESCRIPTION
	"The first output name of master"
    ::= { masterOutputName 1}

masterOutputNameTwo OBJECT-TYPE
    SYNTAX      DisplayString
    MAX-ACCESS  read-write
    STATUS      current
    DESCRIPTION
	"The second output name of master"
    ::= { masterOutputName 2}

masterOutputNameThree OBJECT-TYPE
    SYNTAX      DisplayString
    MAX-ACCESS  read-write
    STATUS      current
    DESCRIPTION
	"The three output name of master"
    ::= { masterOutputName 3}

masterOutputNameFour OBJECT-TYPE
    SYNTAX      DisplayString
    MAX-ACCESS  read-write
    STATUS      current
    DESCRIPTION
	"The four output name of master"
    ::= { masterOutputName 4}

masterOutputNameFive OBJECT-TYPE
    SYNTAX      DisplayString
    MAX-ACCESS  read-write
    STATUS      current
    DESCRIPTION
	"The five output name of master"
    ::= { masterOutputName 5}

masterOutputNameSix OBJECT-TYPE
    SYNTAX      DisplayString
    MAX-ACCESS  read-write
    STATUS      current
    DESCRIPTION
	"The six output name of master"
    ::= { masterOutputName 6}

masterOutputNameSeven OBJECT-TYPE
    SYNTAX      DisplayString
    MAX-ACCESS  read-write
    STATUS      current
    DESCRIPTION
	"The seven output name of master"
    ::= { masterOutputName 7}

masterOutputNameEight OBJECT-TYPE
    SYNTAX      DisplayString
    MAX-ACCESS  read-write
    STATUS      current
    DESCRIPTION
	"The eight output name of master"
    ::= { masterOutputName 8}

masterOutputNameNine OBJECT-TYPE
    SYNTAX      DisplayString
    MAX-ACCESS  read-write
    STATUS      current
    DESCRIPTION
	"The nine output name of master"
    ::= { masterOutputName 9}

masterOutputNameTen OBJECT-TYPE
    SYNTAX      DisplayString
    MAX-ACCESS  read-write
    STATUS      current
    DESCRIPTION
	"The ten output name of master"
    ::= { masterOutputName 10}

masterOutputNameEleven OBJECT-TYPE
    SYNTAX      DisplayString
    MAX-ACCESS  read-write
    STATUS      current
    DESCRIPTION
	"The eleven output name of master"
    ::= { masterOutputName 11}

masterOutputNameTwel OBJECT-TYPE
    SYNTAX      DisplayString
    MAX-ACCESS  read-write
    STATUS      current
    DESCRIPTION
	"The twel output name of master"
    ::= { masterOutputName 12}

masterOutputNameThirteen OBJECT-TYPE
    SYNTAX      DisplayString
    MAX-ACCESS  read-write
    STATUS      current
    DESCRIPTION
	"The thirteen output name of master"
    ::= { masterOutputName 13}

masterOutputNameFourteen OBJECT-TYPE
    SYNTAX      DisplayString
    MAX-ACCESS  read-write
    STATUS      current
    DESCRIPTION
	"The fourteen output name of master"
    ::= { masterOutputName 14}

masterOutputNameFifteen OBJECT-TYPE
    SYNTAX      DisplayString
    MAX-ACCESS  read-write
    STATUS      current
    DESCRIPTION
	"The fifteen output name of master"
    ::= { masterOutputName 15}

masterOutputNameSixteen OBJECT-TYPE
    SYNTAX      DisplayString
    MAX-ACCESS  read-write
    STATUS      current
    DESCRIPTION
	"The sixteen output name of master"
    ::= { masterOutputName 16}

masterOutputNameSeventeen OBJECT-TYPE
    SYNTAX      DisplayString
    MAX-ACCESS  read-write
    STATUS      current
    DESCRIPTION
	"The seventeen output name of master"
    ::= { masterOutputName 17}

masterOutputNameEighteen OBJECT-TYPE
    SYNTAX      DisplayString
    MAX-ACCESS  read-write
    STATUS      current
    DESCRIPTION
	"The eighteen output name of master"
    ::= { masterOutputName 18}
	
masterOutputNameNineteen OBJECT-TYPE
    SYNTAX      DisplayString
    MAX-ACCESS  read-write
    STATUS      current
    DESCRIPTION
	"The nineteen output name of master"
    ::= { masterOutputName 19}
	
masterOutputNametwenty OBJECT-TYPE
    SYNTAX      DisplayString
    MAX-ACCESS  read-write
    STATUS      current
    DESCRIPTION
	"The twenty output name of master"
    ::= { masterOutputName 20}
	
masterOutputNameTwentyone OBJECT-TYPE
    SYNTAX      DisplayString
    MAX-ACCESS  read-write
    STATUS      current
    DESCRIPTION
	"The twenty one output name of master"
    ::= { masterOutputName 21}
	
masterOutputNameTwentytwo OBJECT-TYPE
    SYNTAX      DisplayString
    MAX-ACCESS  read-write
    STATUS      current
    DESCRIPTION
	"The twenty two output name of master"
    ::= { masterOutputName 22}
	
masterOutputNameTwentythree OBJECT-TYPE
    SYNTAX      DisplayString
    MAX-ACCESS  read-write
    STATUS      current
    DESCRIPTION
	"The twenty three output name of master"
    ::= { masterOutputName 23}
	
masterOutputNameTwentyfour OBJECT-TYPE
    SYNTAX      DisplayString
    MAX-ACCESS  read-write
    STATUS      current
    DESCRIPTION
	"The twenty four output name of master"
    ::= { masterOutputName 24}
	
masterOutputNameTwentyfive OBJECT-TYPE
    SYNTAX      DisplayString
    MAX-ACCESS  read-write
    STATUS      current
    DESCRIPTION
	"The twenty five output name of master"
    ::= { masterOutputName 25}
	
masterOutputNameTwentysix OBJECT-TYPE
    SYNTAX      DisplayString
    MAX-ACCESS  read-write
    STATUS      current
    DESCRIPTION
	"The twenty six output name of master"
    ::= { masterOutputName 26}
	
masterOutputNameTwentyseven OBJECT-TYPE
    SYNTAX      DisplayString
    MAX-ACCESS  read-write
    STATUS      current
    DESCRIPTION
	"The twenty seven output name of master"
    ::= { masterOutputName 27}
	
masterOutputNameTwentyeight OBJECT-TYPE
    SYNTAX      DisplayString
    MAX-ACCESS  read-write
    STATUS      current
    DESCRIPTION
	"The twenty eight output name of master"
    ::= { masterOutputName 28}	
masterOutputNameTwentynine OBJECT-TYPE
    SYNTAX      DisplayString
    MAX-ACCESS  read-write
    STATUS      current
    DESCRIPTION
	"The twenty nine output name of master"
    ::= { masterOutputName 29}
	
masterOutputNameThirty OBJECT-TYPE
    SYNTAX      DisplayString
    MAX-ACCESS  read-write
    STATUS      current
    DESCRIPTION
	"The thirty output name of master"
    ::= { masterOutputName 30}
	
masterOutputNameThirtyone OBJECT-TYPE
    SYNTAX      DisplayString
    MAX-ACCESS  read-write
    STATUS      current
    DESCRIPTION
	"The thirty one output name of master"
    ::= { masterOutputName 31}
	
masterOutputNameThirtytwo OBJECT-TYPE
    SYNTAX      DisplayString
    MAX-ACCESS  read-write
    STATUS      current
    DESCRIPTION
	"The thirty two output name of master"
    ::= { masterOutputName 32}
	
masterOutputNameThirtythree OBJECT-TYPE
    SYNTAX      DisplayString
    MAX-ACCESS  read-write
    STATUS      current
    DESCRIPTION
	"The thirty three output name of master"
    ::= { masterOutputName 33}
	
masterOutputNameThirtyfour OBJECT-TYPE
    SYNTAX      DisplayString
    MAX-ACCESS  read-write
    STATUS      current
    DESCRIPTION
	"The thirty four output name of master"
    ::= { masterOutputName 34}
	
masterOutputNameThirtyfive OBJECT-TYPE
    SYNTAX      DisplayString
    MAX-ACCESS  read-write
    STATUS      current
    DESCRIPTION
	"The thirty five output name of master"
    ::= { masterOutputName 35}
	
masterOutputNameThirtysix OBJECT-TYPE
    SYNTAX      DisplayString
    MAX-ACCESS  read-write
    STATUS      current
    DESCRIPTION
	"The thirty six output name of master"
    ::= { masterOutputName 36}
	
masterOutputNameThirtyseven OBJECT-TYPE
    SYNTAX      DisplayString
    MAX-ACCESS  read-write
    STATUS      current
    DESCRIPTION
	"The thirty seven output name of master"
    ::= { masterOutputName 37}
	
masterOutputNameThirtyeight OBJECT-TYPE
    SYNTAX      DisplayString
    MAX-ACCESS  read-write
    STATUS      current
    DESCRIPTION
	"The thirty eight output name of master"
    ::= { masterOutputName 38}
	
masterOutputNameThirtynine OBJECT-TYPE
    SYNTAX      DisplayString
    MAX-ACCESS  read-write
    STATUS      current
    DESCRIPTION
	"The thirty nine output name of master"
    ::= { masterOutputName 39}
	
masterOutputNameFourty OBJECT-TYPE
    SYNTAX      DisplayString
    MAX-ACCESS  read-write
    STATUS      current
    DESCRIPTION
	"The fourty output name of master"
    ::= { masterOutputName 40}
	
masterOutputNameFourtyone OBJECT-TYPE
    SYNTAX      DisplayString
    MAX-ACCESS  read-write
    STATUS      current
    DESCRIPTION
	"The fourty one output name of master"
    ::= { masterOutputName 41}
	
masterOutputNameFourtytwo OBJECT-TYPE
    SYNTAX      DisplayString
    MAX-ACCESS  read-write
    STATUS      current
    DESCRIPTION
	"The fourty two output name of master"
    ::= { masterOutputName 42}	

	
-------------------------------master output delay------------------------	
masterOutputDelay OBJECT IDENTIFIER ::= { master 6}	
masterOutputDelayOne OBJECT-TYPE
    SYNTAX      DisplayString
    MAX-ACCESS  read-write
    STATUS      current
    DESCRIPTION
	"The delay time for ouput one"
    ::= { masterOutputDelay 1}

masterOutputDelayTwo OBJECT-TYPE
    SYNTAX      DisplayString
    MAX-ACCESS  read-write
    STATUS      current
    DESCRIPTION
	"The delay time for ouput two"
    ::= { masterOutputDelay 2}

masterOutputDelayThree OBJECT-TYPE
    SYNTAX      DisplayString
    MAX-ACCESS  read-write
    STATUS      current
    DESCRIPTION
	"The delay time for ouput three"
    ::= { masterOutputDelay 3}

masterOutputDelayFour OBJECT-TYPE
    SYNTAX      DisplayString
    MAX-ACCESS  read-write
    STATUS      current
    DESCRIPTION
	"The delay time for ouput four"
    ::= { masterOutputDelay 4}

masterOutputDelayFive OBJECT-TYPE
    SYNTAX      DisplayString
    MAX-ACCESS  read-write
    STATUS      current
    DESCRIPTION
	"The delay time for ouput five"
    ::= { masterOutputDelay 5}

masterOutputDelaySix OBJECT-TYPE
    SYNTAX      DisplayString
    MAX-ACCESS  read-write
    STATUS      current
    DESCRIPTION
	"The delay time for ouput six"
    ::= { masterOutputDelay 6}

masterOutputDelaySeven OBJECT-TYPE
    SYNTAX      DisplayString
    MAX-ACCESS  read-write
    STATUS      current
    DESCRIPTION
	"The delay time for ouput seven"
    ::= { masterOutputDelay 7}

masterOutputDelayEight OBJECT-TYPE
    SYNTAX      DisplayString
    MAX-ACCESS  read-write
    STATUS      current
    DESCRIPTION
	"The delay time for ouput eight"
    ::= { masterOutputDelay 8}

masterOutputDelayNine OBJECT-TYPE
    SYNTAX      DisplayString
    MAX-ACCESS  read-write
    STATUS      current
    DESCRIPTION
	"The delay time for ouput nine"
    ::= { masterOutputDelay 9}

masterOutputDelayTen OBJECT-TYPE
    SYNTAX      DisplayString
    MAX-ACCESS  read-write
    STATUS      current
    DESCRIPTION
	"The delay time for ouput ten"
    ::= { masterOutputDelay 10}

masterOutputDelayEleven OBJECT-TYPE
    SYNTAX      DisplayString
    MAX-ACCESS  read-write
    STATUS      current
    DESCRIPTION
	"The delay time for ouput eleven"
    ::= { masterOutputDelay 11}

masterOutputDelayTwel OBJECT-TYPE
    SYNTAX      DisplayString
    MAX-ACCESS  read-write
    STATUS      current
    DESCRIPTION
	"The delay time for ouput twel"
    ::= { masterOutputDelay 12}

masterOutputDelayThirteen OBJECT-TYPE
    SYNTAX      DisplayString
    MAX-ACCESS  read-write
    STATUS      current
    DESCRIPTION
	"The delay time for ouput thirteen"
    ::= { masterOutputDelay 13}

masterOutputDelayFourteen OBJECT-TYPE
    SYNTAX      DisplayString
    MAX-ACCESS  read-write
    STATUS      current
    DESCRIPTION
	"The delay time for ouput fourteen"
    ::= { masterOutputDelay 14}

masterOutputDelayFifteen OBJECT-TYPE
    SYNTAX      DisplayString
    MAX-ACCESS  read-write
    STATUS      current
    DESCRIPTION
	"The delay time for ouput fifteen"
    ::= { masterOutputDelay 15}

masterOutputDelaySixteen OBJECT-TYPE
    SYNTAX      DisplayString
    MAX-ACCESS  read-write
    STATUS      current
    DESCRIPTION
	"The delay time for ouput sixteen"
    ::= { masterOutputDelay 16}

masterOutputDelaySeventeen OBJECT-TYPE
    SYNTAX      DisplayString
    MAX-ACCESS  read-write
    STATUS      current
    DESCRIPTION
	"The delay time for ouput seventeen"
    ::= { masterOutputDelay 17}

masterOutputDelayEighteen OBJECT-TYPE
    SYNTAX      DisplayString
    MAX-ACCESS  read-write
    STATUS      current
    DESCRIPTION
	"The delay time for ouput eighteen"
    ::= { masterOutputDelay 18}
	
masterOutputDelayNineteen OBJECT-TYPE
    SYNTAX      DisplayString
    MAX-ACCESS  read-write
    STATUS      current
    DESCRIPTION
	"The delay time for ouput nineteen"
    ::= { masterOutputDelay 19}
	
masterOutputDelaytwenty OBJECT-TYPE
    SYNTAX      DisplayString
    MAX-ACCESS  read-write
    STATUS      current
    DESCRIPTION
	"The delay time for ouput twenty"
    ::= { masterOutputDelay 20}
	
masterOutputDelayTwentyone OBJECT-TYPE
    SYNTAX      DisplayString
    MAX-ACCESS  read-write
    STATUS      current
    DESCRIPTION
	"The delay time for ouput twenty one"
    ::= { masterOutputDelay 21}
	
masterOutputDelayTwentyonetwo OBJECT-TYPE
    SYNTAX      DisplayString
    MAX-ACCESS  read-write
    STATUS      current
    DESCRIPTION
	"The delay time for ouput twenty two"
    ::= { masterOutputDelay 22}
	
masterOutputDelayTwentythree OBJECT-TYPE
    SYNTAX      DisplayString
    MAX-ACCESS  read-write
    STATUS      current
    DESCRIPTION
	"The delay time for ouput twenty three"
    ::= { masterOutputDelay 23}
	
masterOutputDelayTwentyfour OBJECT-TYPE
    SYNTAX      DisplayString
    MAX-ACCESS  read-write
    STATUS      current
    DESCRIPTION
	"The delay time for ouput twenty four"
    ::= { masterOutputDelay 24}
	
masterOutputDelayTwentyfive OBJECT-TYPE
    SYNTAX      DisplayString
    MAX-ACCESS  read-write
    STATUS      current
    DESCRIPTION
	"The delay time for ouput twenty five"
    ::= { masterOutputDelay 25}
	
masterOutputDelayTwentysix OBJECT-TYPE
    SYNTAX      DisplayString
    MAX-ACCESS  read-write
    STATUS      current
    DESCRIPTION
	"The delay time for ouput twenty six"
    ::= { masterOutputDelay 26}
	
masterOutputDelayTwentyseven OBJECT-TYPE
    SYNTAX      DisplayString
    MAX-ACCESS  read-write
    STATUS      current
    DESCRIPTION
	"The delay time for ouput twenty seven"
    ::= { masterOutputDelay 27}
	
masterOutputDelayTwentyeight OBJECT-TYPE
    SYNTAX      DisplayString
    MAX-ACCESS  read-write
    STATUS      current
    DESCRIPTION
	"The delay time for ouput twenty eight"
    ::= { masterOutputDelay 28}	
masterOutputDelayTwentynine OBJECT-TYPE
    SYNTAX      DisplayString
    MAX-ACCESS  read-write
    STATUS      current
    DESCRIPTION
	"The delay time for ouput twenty nine"
    ::= { masterOutputDelay 29}
	
masterOutputDelayThirty OBJECT-TYPE
    SYNTAX      DisplayString
    MAX-ACCESS  read-write
    STATUS      current
    DESCRIPTION
	"The delay time for ouput thirty"
    ::= { masterOutputDelay 30}
	
masterOutputDelayThirtyone OBJECT-TYPE
    SYNTAX      DisplayString
    MAX-ACCESS  read-write
    STATUS      current
    DESCRIPTION
	"The delay time for ouput thirty one"
    ::= { masterOutputDelay 31}
	
masterOutputDelayThirtytwo OBJECT-TYPE
    SYNTAX      DisplayString
    MAX-ACCESS  read-write
    STATUS      current
    DESCRIPTION
	"The delay time for ouput thirty two"
    ::= { masterOutputDelay 32}
	
masterOutputDelayThirtythree OBJECT-TYPE
    SYNTAX      DisplayString
    MAX-ACCESS  read-write
    STATUS      current
    DESCRIPTION
	"The delay time for ouput thirty three"
    ::= { masterOutputDelay 33}
	
masterOutputDelayThirtyfour OBJECT-TYPE
    SYNTAX      DisplayString
    MAX-ACCESS  read-write
    STATUS      current
    DESCRIPTION
	"The delay time for ouput thirty four"
    ::= { masterOutputDelay 34}
	
masterOutputDelayThirtyfive OBJECT-TYPE
    SYNTAX      DisplayString
    MAX-ACCESS  read-write
    STATUS      current
    DESCRIPTION
	"The delay time for ouput thirty five"
    ::= { masterOutputDelay 35}
	
masterOutputDelayThirtysix OBJECT-TYPE
    SYNTAX      DisplayString
    MAX-ACCESS  read-write
    STATUS      current
    DESCRIPTION
	"The delay time for ouput thirty six"
    ::= { masterOutputDelay 36}
	
masterOutputDelayThirtyseven OBJECT-TYPE
    SYNTAX      DisplayString
    MAX-ACCESS  read-write
    STATUS      current
    DESCRIPTION
	"The delay time for ouput thirty seven"
    ::= { masterOutputDelay 37}
	
masterOutputDelayThirtyeight OBJECT-TYPE
    SYNTAX      DisplayString
    MAX-ACCESS  read-write
    STATUS      current
    DESCRIPTION
	"The delay time for ouput thirty eight"
    ::= { masterOutputDelay 38}
	
masterOutputDelayThirtynine OBJECT-TYPE
    SYNTAX      DisplayString
    MAX-ACCESS  read-write
    STATUS      current
    DESCRIPTION
	"The delay time for ouput thirty nine"
    ::= { masterOutputDelay 39}
	
masterOutputDelayFourty OBJECT-TYPE
    SYNTAX      DisplayString
    MAX-ACCESS  read-write
    STATUS      current
    DESCRIPTION
	"The delay time for ouput fourty"
    ::= { masterOutputDelay 40}
	
masterOutputDelayFourtyone OBJECT-TYPE
    SYNTAX      DisplayString
    MAX-ACCESS  read-write
    STATUS      current
    DESCRIPTION
	"The delay time for ouput fouryt one"
    ::= { masterOutputDelay 41}
	
masterOutputDelayFourtytwo OBJECT-TYPE
    SYNTAX      DisplayString
    MAX-ACCESS  read-write
    STATUS      current
    DESCRIPTION
	"The delay time for ouput fourty two"
    ::= { masterOutputDelay 42}

	
-------------------------------master output switch------------------------	
masterOutputSwitch OBJECT IDENTIFIER ::= { master 7}		
masterOutputSwitchOne OBJECT-TYPE
    SYNTAX      DisplayString
    MAX-ACCESS  read-write
    STATUS      current
    DESCRIPTION
	"The output switch one of master"
    ::= { masterOutputSwitch 1}

masterOutputSwitchTwo OBJECT-TYPE
    SYNTAX      DisplayString
    MAX-ACCESS  read-write
    STATUS      current
    DESCRIPTION
	"The output switch two of master"
    ::= { masterOutputSwitch 2}

masterOutputSwitchThree OBJECT-TYPE
    SYNTAX      DisplayString
    MAX-ACCESS  read-write
    STATUS      current
    DESCRIPTION
	"The output switch three of master"
    ::= { masterOutputSwitch 3}

masterOutputSwitchFour OBJECT-TYPE
    SYNTAX      DisplayString
    MAX-ACCESS  read-write
    STATUS      current
    DESCRIPTION
	"The output switch four of master"
    ::= { masterOutputSwitch 4}

masterOutputSwitchFive OBJECT-TYPE
    SYNTAX      DisplayString
    MAX-ACCESS  read-write
    STATUS      current
    DESCRIPTION
	"The output switch five of master"
    ::= { masterOutputSwitch 5}

masterOutputSwitchSix OBJECT-TYPE
    SYNTAX      DisplayString
    MAX-ACCESS  read-write
    STATUS      current
    DESCRIPTION
	"The output switch six of master"
    ::= { masterOutputSwitch 6}

masterOutputSwitchSeven OBJECT-TYPE
    SYNTAX      DisplayString
    MAX-ACCESS  read-write
    STATUS      current
    DESCRIPTION
	"The output switch seven of master"
    ::= { masterOutputSwitch 7}

masterOutputSwitchEight OBJECT-TYPE
    SYNTAX      DisplayString
    MAX-ACCESS  read-write
    STATUS      current
    DESCRIPTION
	"The output switch eight of master"
    ::= { masterOutputSwitch 8}

masterOutputSwitchNine OBJECT-TYPE
    SYNTAX      DisplayString
    MAX-ACCESS  read-write
    STATUS      current
    DESCRIPTION
	"The output switch nine of master"
    ::= { masterOutputSwitch 9}

masterOutputSwitchTen OBJECT-TYPE
    SYNTAX      DisplayString
    MAX-ACCESS  read-write
    STATUS      current
    DESCRIPTION
	"The output switch ten of master"
    ::= { masterOutputSwitch 10}

masterOutputSwitchEleven OBJECT-TYPE
    SYNTAX      DisplayString
    MAX-ACCESS  read-write
    STATUS      current
    DESCRIPTION
	"The output switch eleven of master"
    ::= { masterOutputSwitch 11}

masterOutputSwitchTwel OBJECT-TYPE
    SYNTAX      DisplayString
    MAX-ACCESS  read-write
    STATUS      current
    DESCRIPTION
	"The output switch twel of master"
    ::= { masterOutputSwitch 12}

masterOutputSwitchThirteen OBJECT-TYPE
    SYNTAX      DisplayString
    MAX-ACCESS  read-write
    STATUS      current
    DESCRIPTION
	"The output switch thirteen of master"
    ::= { masterOutputSwitch 13}

masterOutputSwitchFourteen OBJECT-TYPE
    SYNTAX      DisplayString
    MAX-ACCESS  read-write
    STATUS      current
    DESCRIPTION
	"The output switch fourteen of master"
    ::= { masterOutputSwitch 14}

masterOutputSwitchFifteen OBJECT-TYPE
    SYNTAX      DisplayString
    MAX-ACCESS  read-write
    STATUS      current
    DESCRIPTION
	"The output switch fifteen of master"
    ::= { masterOutputSwitch 15}

masterOutputSwitchSixteen OBJECT-TYPE
    SYNTAX      DisplayString
    MAX-ACCESS  read-write
    STATUS      current
    DESCRIPTION
	"The output switch sixteen of master"
    ::= { masterOutputSwitch 16}

masterOutputSwitchSeventeen OBJECT-TYPE
    SYNTAX      DisplayString
    MAX-ACCESS  read-write
    STATUS      current
    DESCRIPTION
	"The output switch seventeen of master"
    ::= { masterOutputSwitch 17}

masterOutputSwitchEighteen OBJECT-TYPE
    SYNTAX      DisplayString
    MAX-ACCESS  read-write
    STATUS      current
    DESCRIPTION
	"The output switch eighteen of master"
    ::= { masterOutputSwitch 18}
	
masterOutputSwitchNineteen OBJECT-TYPE
    SYNTAX      DisplayString
    MAX-ACCESS  read-write
    STATUS      current
    DESCRIPTION
	"The output switch nineteen of master"
    ::= { masterOutputSwitch 19}
	
masterOutputSwitchtwenty OBJECT-TYPE
    SYNTAX      DisplayString
    MAX-ACCESS  read-write
    STATUS      current
    DESCRIPTION
	"The output switch twenty of master"
    ::= { masterOutputSwitch 20}
	
masterOutputSwitchTwentyone OBJECT-TYPE
    SYNTAX      DisplayString
    MAX-ACCESS  read-write
    STATUS      current
    DESCRIPTION
	"The output switch twenty one of master"
    ::= { masterOutputSwitch 21}
	
masterOutputSwitchTwentyonetwo OBJECT-TYPE
    SYNTAX      DisplayString
    MAX-ACCESS  read-write
    STATUS      current
    DESCRIPTION
	"The output switch twenty two of master"
    ::= { masterOutputSwitch 22}
	
masterOutputSwitchTwentythree OBJECT-TYPE
    SYNTAX      DisplayString
    MAX-ACCESS  read-write
    STATUS      current
    DESCRIPTION
	"The output switch twenty three of master"
    ::= { masterOutputSwitch 23}
	
masterOutputSwitchTwentyfour OBJECT-TYPE
    SYNTAX      DisplayString
    MAX-ACCESS  read-write
    STATUS      current
    DESCRIPTION
	"The output switch twenty four of master"
    ::= { masterOutputSwitch 24}
	
masterOutputSwitchTwentyfive OBJECT-TYPE
    SYNTAX      DisplayString
    MAX-ACCESS  read-write
    STATUS      current
    DESCRIPTION
	"The output switch twenty five of master"
    ::= { masterOutputSwitch 25}
	
masterOutputSwitchTwentysix OBJECT-TYPE
    SYNTAX      DisplayString
    MAX-ACCESS  read-write
    STATUS      current
    DESCRIPTION
	"The output switch twenty six of master"
    ::= { masterOutputSwitch 26}
	
masterOutputSwitchTwentyseven OBJECT-TYPE
    SYNTAX      DisplayString
    MAX-ACCESS  read-write
    STATUS      current
    DESCRIPTION
	"The output switch twenty seven of master"
    ::= { masterOutputSwitch 27}
	
masterOutputSwitchTwentyeight OBJECT-TYPE
    SYNTAX      DisplayString
    MAX-ACCESS  read-write
    STATUS      current
    DESCRIPTION
	"The output switch twenty eight of master"
    ::= { masterOutputSwitch 28}	
masterOutputSwitchTwentynine OBJECT-TYPE
    SYNTAX      DisplayString
    MAX-ACCESS  read-write
    STATUS      current
    DESCRIPTION
	"The output switch twenty nine of master"
    ::= { masterOutputSwitch 29}
	
masterOutputSwitchThirty OBJECT-TYPE
    SYNTAX      DisplayString
    MAX-ACCESS  read-write
    STATUS      current
    DESCRIPTION
	"The output switch thirty of master"
    ::= { masterOutputSwitch 30}
	
masterOutputSwitchThirtyone OBJECT-TYPE
    SYNTAX      DisplayString
    MAX-ACCESS  read-write
    STATUS      current
    DESCRIPTION
	"The output switch thirty one of master"
    ::= { masterOutputSwitch 31}
	
masterOutputSwitchThirtytwo OBJECT-TYPE
    SYNTAX      DisplayString
    MAX-ACCESS  read-write
    STATUS      current
    DESCRIPTION
	"The output switch thirty two of master"
    ::= { masterOutputSwitch 32}
	
masterOutputSwitchThirtythree OBJECT-TYPE
    SYNTAX      DisplayString
    MAX-ACCESS  read-write
    STATUS      current
    DESCRIPTION
	"The output switch thirty three of master"
    ::= { masterOutputSwitch 33}
	
masterOutputSwitchThirtyfour OBJECT-TYPE
    SYNTAX      DisplayString
    MAX-ACCESS  read-write
    STATUS      current
    DESCRIPTION
	"The output switch thirty four of master"
    ::= { masterOutputSwitch 34}
	
masterOutputSwitchThirtyfive OBJECT-TYPE
    SYNTAX      DisplayString
    MAX-ACCESS  read-write
    STATUS      current
    DESCRIPTION
	"The output switch thirty five of master"
    ::= { masterOutputSwitch 35}
	
masterOutputSwitchThirtysix OBJECT-TYPE
    SYNTAX      DisplayString
    MAX-ACCESS  read-write
    STATUS      current
    DESCRIPTION
	"The output switch thirty six of master"
    ::= { masterOutputSwitch 36}
	
masterOutputSwitchThirtyseven OBJECT-TYPE
    SYNTAX      DisplayString
    MAX-ACCESS  read-write
    STATUS      current
    DESCRIPTION
	"The output switch thirty seven of master"
    ::= { masterOutputSwitch 37}
	
masterOutputSwitchThirtyeight OBJECT-TYPE
    SYNTAX      DisplayString
    MAX-ACCESS  read-write
    STATUS      current
    DESCRIPTION
	"The output switch thirty eight of master"
    ::= { masterOutputSwitch 38}
	
masterOutputSwitchThirtynine OBJECT-TYPE
    SYNTAX      DisplayString
    MAX-ACCESS  read-write
    STATUS      current
    DESCRIPTION
	"The output switch thirty nine of master"
    ::= { masterOutputSwitch 39}
	
masterOutputSwitchFourty OBJECT-TYPE
    SYNTAX      DisplayString
    MAX-ACCESS  read-write
    STATUS      current
    DESCRIPTION
	"The output switch fourty of master"
    ::= { masterOutputSwitch 40}
	
masterOutputSwitchFourtyone OBJECT-TYPE
    SYNTAX      DisplayString
    MAX-ACCESS  read-write
    STATUS      current
    DESCRIPTION
	"The output switch fourty one of master"
    ::= { masterOutputSwitch 41}
	
masterOutputSwitchFourtytwo OBJECT-TYPE
    SYNTAX      DisplayString
    MAX-ACCESS  read-write
    STATUS      current
    DESCRIPTION
	"The output switch fourty two of master"
    ::= { masterOutputSwitch 42}

	
-------------------------------master output current------------------------	
masterOutputCurrent OBJECT IDENTIFIER ::= { master 8}		
masterOutputCurrentValue OBJECT IDENTIFIER ::= { masterOutputCurrent 1}	

masterOutputCurrentValueOne OBJECT-TYPE
    SYNTAX      DisplayString
    MAX-ACCESS  read-write
    STATUS      current
    DESCRIPTION
	"The current value of output one"
    ::= { masterOutputCurrentValue 1}

masterOutputCurrentValueTwo OBJECT-TYPE
    SYNTAX      DisplayString
    MAX-ACCESS  read-write
    STATUS      current
    DESCRIPTION
	"The current value of output two"
    ::= { masterOutputCurrentValue 2}

masterOutputCurrentValueThree OBJECT-TYPE
    SYNTAX      DisplayString
    MAX-ACCESS  read-write
    STATUS      current
    DESCRIPTION
	"The current value of output three"
    ::= { masterOutputCurrentValue 3}

masterOutputCurrentValueFour OBJECT-TYPE
    SYNTAX      DisplayString
    MAX-ACCESS  read-write
    STATUS      current
    DESCRIPTION
	"The current value of output four"
    ::= { masterOutputCurrentValue 4}

masterOutputCurrentValueFive OBJECT-TYPE
    SYNTAX      DisplayString
    MAX-ACCESS  read-write
    STATUS      current
    DESCRIPTION
	"The current value of output five"
    ::= { masterOutputCurrentValue 5}

masterOutputCurrentValueSix OBJECT-TYPE
    SYNTAX      DisplayString
    MAX-ACCESS  read-write
    STATUS      current
    DESCRIPTION
	"The current value of output six"
    ::= { masterOutputCurrentValue 6}

masterOutputCurrentValueSeven OBJECT-TYPE
    SYNTAX      DisplayString
    MAX-ACCESS  read-write
    STATUS      current
    DESCRIPTION
	"The current value of output seven"
    ::= { masterOutputCurrentValue 7}

masterOutputCurrentValueEight OBJECT-TYPE
    SYNTAX      DisplayString
    MAX-ACCESS  read-write
    STATUS      current
    DESCRIPTION
	"The current value of output eight"
    ::= { masterOutputCurrentValue 8}

masterOutputCurrentValueNine OBJECT-TYPE
    SYNTAX      DisplayString
    MAX-ACCESS  read-write
    STATUS      current
    DESCRIPTION
	"The current value of output nine"
    ::= { masterOutputCurrentValue 9}

masterOutputCurrentValueTen OBJECT-TYPE
    SYNTAX      DisplayString
    MAX-ACCESS  read-write
    STATUS      current
    DESCRIPTION
	"The current value of output ten"
    ::= { masterOutputCurrentValue 10}

masterOutputCurrentValueEleven OBJECT-TYPE
    SYNTAX      DisplayString
    MAX-ACCESS  read-write
    STATUS      current
    DESCRIPTION
	"The current value of output eleven"
    ::= { masterOutputCurrentValue 11}

masterOutputCurrentValueTwel OBJECT-TYPE
    SYNTAX      DisplayString
    MAX-ACCESS  read-write
    STATUS      current
    DESCRIPTION
	"The current value of output twel"
    ::= { masterOutputCurrentValue 12}

masterOutputCurrentValueThirteen OBJECT-TYPE
    SYNTAX      DisplayString
    MAX-ACCESS  read-write
    STATUS      current
    DESCRIPTION
	"The current value of output thirteen"
    ::= { masterOutputCurrentValue 13}

masterOutputCurrentValueFourteen OBJECT-TYPE
    SYNTAX      DisplayString
    MAX-ACCESS  read-write
    STATUS      current
    DESCRIPTION
	"The current value of output fourteen"
    ::= { masterOutputCurrentValue 14}

masterOutputCurrentValueFifteen OBJECT-TYPE
    SYNTAX      DisplayString
    MAX-ACCESS  read-write
    STATUS      current
    DESCRIPTION
	"The current value of output fifteen"
    ::= { masterOutputCurrentValue 15}

masterOutputCurrentValueSixteen OBJECT-TYPE
    SYNTAX      DisplayString
    MAX-ACCESS  read-write
    STATUS      current
    DESCRIPTION
	"The current value of output sixteen"
    ::= { masterOutputCurrentValue 16}

masterOutputCurrentValueSeventeen OBJECT-TYPE
    SYNTAX      DisplayString
    MAX-ACCESS  read-write
    STATUS      current
    DESCRIPTION
	"The current value of output seventeen"
    ::= { masterOutputCurrentValue 17}

masterOutputCurrentValueEighteen OBJECT-TYPE
    SYNTAX      DisplayString
    MAX-ACCESS  read-write
    STATUS      current
    DESCRIPTION
	"The current value of output eighteen"
    ::= { masterOutputCurrentValue 18}
	
masterOutputCurrentValueNineteen OBJECT-TYPE
    SYNTAX      DisplayString
    MAX-ACCESS  read-write
    STATUS      current
    DESCRIPTION
	"The current value of output nineteen"
    ::= { masterOutputCurrentValue 19}
	
masterOutputCurrentValuetwenty OBJECT-TYPE
    SYNTAX      DisplayString
    MAX-ACCESS  read-write
    STATUS      current
    DESCRIPTION
	"The current value of output twenty"
    ::= { masterOutputCurrentValue 20}
	
masterOutputCurrentValueTwentyone OBJECT-TYPE
    SYNTAX      DisplayString
    MAX-ACCESS  read-write
    STATUS      current
    DESCRIPTION
	"The current value of output twenty one"
    ::= { masterOutputCurrentValue 21}
	
masterOutputCurrentValueTwentyonetwo OBJECT-TYPE
    SYNTAX      DisplayString
    MAX-ACCESS  read-write
    STATUS      current
    DESCRIPTION
	"The current value of output twenty two"
    ::= { masterOutputCurrentValue 22}
	
masterOutputCurrentValueTwentythree OBJECT-TYPE
    SYNTAX      DisplayString
    MAX-ACCESS  read-write
    STATUS      current
    DESCRIPTION
	"The current value of output twenty three"
    ::= { masterOutputCurrentValue 23}
	
masterOutputCurrentValueTwentyfour OBJECT-TYPE
    SYNTAX      DisplayString
    MAX-ACCESS  read-write
    STATUS      current
    DESCRIPTION
	"The current value of output twenty four"
    ::= { masterOutputCurrentValue 24}
	
masterOutputCurrentValueTwentyfive OBJECT-TYPE
    SYNTAX      DisplayString
    MAX-ACCESS  read-write
    STATUS      current
    DESCRIPTION
	"The current value of output twenty five"
    ::= { masterOutputCurrentValue 25}
	
masterOutputCurrentValueTwentysix OBJECT-TYPE
    SYNTAX      DisplayString
    MAX-ACCESS  read-write
    STATUS      current
    DESCRIPTION
	"The current value of output twenty six"
    ::= { masterOutputCurrentValue 26}
	
masterOutputCurrentValueTwentyseven OBJECT-TYPE
    SYNTAX      DisplayString
    MAX-ACCESS  read-write
    STATUS      current
    DESCRIPTION
	"The current value of output twenty seven"
    ::= { masterOutputCurrentValue 27}
	
masterOutputCurrentValueTwentyeight OBJECT-TYPE
    SYNTAX      DisplayString
    MAX-ACCESS  read-write
    STATUS      current
    DESCRIPTION
	"The current value of output twenty eight"
    ::= { masterOutputCurrentValue 28}	
masterOutputCurrentValueTwentynine OBJECT-TYPE
    SYNTAX      DisplayString
    MAX-ACCESS  read-write
    STATUS      current
    DESCRIPTION
	"The current value of output twenty nine"
    ::= { masterOutputCurrentValue 29}
	
masterOutputCurrentValueThirty OBJECT-TYPE
    SYNTAX      DisplayString
    MAX-ACCESS  read-write
    STATUS      current
    DESCRIPTION
	"The current value of output thirty"
    ::= { masterOutputCurrentValue 30}
	
masterOutputCurrentValueThirtyone OBJECT-TYPE
    SYNTAX      DisplayString
    MAX-ACCESS  read-write
    STATUS      current
    DESCRIPTION
	"The current value of output thirty one"
    ::= { masterOutputCurrentValue 31}
	
masterOutputCurrentValueThirtytwo OBJECT-TYPE
    SYNTAX      DisplayString
    MAX-ACCESS  read-write
    STATUS      current
    DESCRIPTION
	"The current value of output thirty two"
    ::= { masterOutputCurrentValue 32}
	
masterOutputCurrentValueThirtythree OBJECT-TYPE
    SYNTAX      DisplayString
    MAX-ACCESS  read-write
    STATUS      current
    DESCRIPTION
	"The current value of output thirty three"
    ::= { masterOutputCurrentValue 33}
	
masterOutputCurrentValueThirtyfour OBJECT-TYPE
    SYNTAX      DisplayString
    MAX-ACCESS  read-write
    STATUS      current
    DESCRIPTION
	"The current value of output thirty four"
    ::= { masterOutputCurrentValue 34}
	
masterOutputCurrentValueThirtyfive OBJECT-TYPE
    SYNTAX      DisplayString
    MAX-ACCESS  read-write
    STATUS      current
    DESCRIPTION
	"The current value of output thirty five"
    ::= { masterOutputCurrentValue 35}
	
masterOutputCurrentValueThirtysix OBJECT-TYPE
    SYNTAX      DisplayString
    MAX-ACCESS  read-write
    STATUS      current
    DESCRIPTION
	"The current value of output thirty six"
    ::= { masterOutputCurrentValue 36}
	
masterOutputCurrentValueThirtyseven OBJECT-TYPE
    SYNTAX      DisplayString
    MAX-ACCESS  read-write
    STATUS      current
    DESCRIPTION
	"The current value of output thirty seven"
    ::= { masterOutputCurrentValue 37}
	
masterOutputCurrentValueThirtyeight OBJECT-TYPE
    SYNTAX      DisplayString
    MAX-ACCESS  read-write
    STATUS      current
    DESCRIPTION
	"The current value of output thirty eight"
    ::= { masterOutputCurrentValue 38}
	
masterOutputCurrentValueThirtynine OBJECT-TYPE
    SYNTAX      DisplayString
    MAX-ACCESS  read-write
    STATUS      current
    DESCRIPTION
	"The current value of output thirty nine"
    ::= { masterOutputCurrentValue 39}
	
masterOutputCurrentValueFourty OBJECT-TYPE
    SYNTAX      DisplayString
    MAX-ACCESS  read-write
    STATUS      current
    DESCRIPTION
	"The current value of output fourty"
    ::= { masterOutputCurrentValue 40}
	
masterOutputCurrentValueFourtyone OBJECT-TYPE
    SYNTAX      DisplayString
    MAX-ACCESS  read-write
    STATUS      current
    DESCRIPTION
	"The current value of output fourty one"
    ::= { masterOutputCurrentValue 41}
	
masterOutputCurrentValueFourtytwo OBJECT-TYPE
    SYNTAX      DisplayString
    MAX-ACCESS  read-write
    STATUS      current
    DESCRIPTION
	"The current value of output fourty two"
    ::= { masterOutputCurrentValue 42}


-------------------------------master output current Min------------------------			
masterOutputCurrentMin OBJECT IDENTIFIER ::= { masterOutputCurrent 2}	

masterOutputCurrentMinOne OBJECT-TYPE
    SYNTAX      DisplayString
    MAX-ACCESS  read-write
    STATUS      current
    DESCRIPTION
	"The Min. current alarm value of output one of master"
    ::= { masterOutputCurrentMin 1}

masterOutputCurrentMinTwo OBJECT-TYPE
    SYNTAX      DisplayString
    MAX-ACCESS  read-write
    STATUS      current
    DESCRIPTION
	"TThe Min. current alarm value of output two of master"
    ::= { masterOutputCurrentMin 2}

masterOutputCurrentMinThree OBJECT-TYPE
    SYNTAX      DisplayString
    MAX-ACCESS  read-write
    STATUS      current
    DESCRIPTION
	"TThe Min. current alarm value of output three of master"
    ::= { masterOutputCurrentMin 3}

masterOutputCurrentMinFour OBJECT-TYPE
    SYNTAX      DisplayString
    MAX-ACCESS  read-write
    STATUS      current
    DESCRIPTION
	"TThe Min. current alarm value of output four of master"
    ::= { masterOutputCurrentMin 4}

masterOutputCurrentMinFive OBJECT-TYPE
    SYNTAX      DisplayString
    MAX-ACCESS  read-write
    STATUS      current
    DESCRIPTION
	"TThe Min. current alarm value of output five of master"
    ::= { masterOutputCurrentMin 5}

masterOutputCurrentMinSix OBJECT-TYPE
    SYNTAX      DisplayString
    MAX-ACCESS  read-write
    STATUS      current
    DESCRIPTION
	"TThe Min. current alarm value of output six of master"
    ::= { masterOutputCurrentMin 6}

masterOutputCurrentMinSeven OBJECT-TYPE
    SYNTAX      DisplayString
    MAX-ACCESS  read-write
    STATUS      current
    DESCRIPTION
	"TThe Min. current alarm value of output seven of master"
    ::= { masterOutputCurrentMin 7}

masterOutputCurrentMinEight OBJECT-TYPE
    SYNTAX      DisplayString
    MAX-ACCESS  read-write
    STATUS      current
    DESCRIPTION
	"TThe Min. current alarm value of output eight of master"
    ::= { masterOutputCurrentMin 8}

masterOutputCurrentMinNine OBJECT-TYPE
    SYNTAX      DisplayString
    MAX-ACCESS  read-write
    STATUS      current
    DESCRIPTION
	"TThe Min. current alarm value of output nine of master"
    ::= { masterOutputCurrentMin 9}

masterOutputCurrentMinTen OBJECT-TYPE
    SYNTAX      DisplayString
    MAX-ACCESS  read-write
    STATUS      current
    DESCRIPTION
	"TThe Min. current alarm value of output ten of master"
    ::= { masterOutputCurrentMin 10}

masterOutputCurrentMinEleven OBJECT-TYPE
    SYNTAX      DisplayString
    MAX-ACCESS  read-write
    STATUS      current
    DESCRIPTION
	"TThe Min. current alarm value of output eleven of master"
    ::= { masterOutputCurrentMin 11}

masterOutputCurrentMinTwel OBJECT-TYPE
    SYNTAX      DisplayString
    MAX-ACCESS  read-write
    STATUS      current
    DESCRIPTION
	"TThe Min. current alarm value of output twel of master"
    ::= { masterOutputCurrentMin 12}

masterOutputCurrentMinThirteen OBJECT-TYPE
    SYNTAX      DisplayString
    MAX-ACCESS  read-write
    STATUS      current
    DESCRIPTION
	"TThe Min. current alarm value of output thirteen of master"
    ::= { masterOutputCurrentMin 13}

masterOutputCurrentMinFourteen OBJECT-TYPE
    SYNTAX      DisplayString
    MAX-ACCESS  read-write
    STATUS      current
    DESCRIPTION
	"TThe Min. current alarm value of output fourteen of master"
    ::= { masterOutputCurrentMin 14}

masterOutputCurrentMinFifteen OBJECT-TYPE
    SYNTAX      DisplayString
    MAX-ACCESS  read-write
    STATUS      current
    DESCRIPTION
	"TThe Min. current alarm value of output fifteen of master"
    ::= { masterOutputCurrentMin 15}

masterOutputCurrentMinSixteen OBJECT-TYPE
    SYNTAX      DisplayString
    MAX-ACCESS  read-write
    STATUS      current
    DESCRIPTION
	"TThe Min. current alarm value of output sixteen of master"
    ::= { masterOutputCurrentMin 16}

masterOutputCurrentMinSeventeen OBJECT-TYPE
    SYNTAX      DisplayString
    MAX-ACCESS  read-write
    STATUS      current
    DESCRIPTION
	"TThe Min. current alarm value of output seventeen of master"
    ::= { masterOutputCurrentMin 17}

masterOutputCurrentMinEighteen OBJECT-TYPE
    SYNTAX      DisplayString
    MAX-ACCESS  read-write
    STATUS      current
    DESCRIPTION
	"TThe Min. current alarm value of output eighteen of master"
    ::= { masterOutputCurrentMin 18}
	
masterOutputCurrentMinNineteen OBJECT-TYPE
    SYNTAX      DisplayString
    MAX-ACCESS  read-write
    STATUS      current
    DESCRIPTION
	"TThe Min. current alarm value of output nineteen of master"
    ::= { masterOutputCurrentMin 19}
	
masterOutputCurrentMintwenty OBJECT-TYPE
    SYNTAX      DisplayString
    MAX-ACCESS  read-write
    STATUS      current
    DESCRIPTION
	"TThe Min. current alarm value of output twenty of master"
    ::= { masterOutputCurrentMin 20}
	
masterOutputCurrentMinTwentyone OBJECT-TYPE
    SYNTAX      DisplayString
    MAX-ACCESS  read-write
    STATUS      current
    DESCRIPTION
	"TThe Min. current alarm value of output twenty one of master"
    ::= { masterOutputCurrentMin 21}
	
masterOutputCurrentMinTwentyonetwo OBJECT-TYPE
    SYNTAX      DisplayString
    MAX-ACCESS  read-write
    STATUS      current
    DESCRIPTION
	"TThe Min. current alarm value of output twenty two of master"
    ::= { masterOutputCurrentMin 22}
	
masterOutputCurrentMinTwentythree OBJECT-TYPE
    SYNTAX      DisplayString
    MAX-ACCESS  read-write
    STATUS      current
    DESCRIPTION
	"TThe Min. current alarm value of output twenty three of master"
    ::= { masterOutputCurrentMin 23}
	
masterOutputCurrentMinTwentyfour OBJECT-TYPE
    SYNTAX      DisplayString
    MAX-ACCESS  read-write
    STATUS      current
    DESCRIPTION
	"TThe Min. current alarm value of output twenty four of master"
    ::= { masterOutputCurrentMin 24}
	
masterOutputCurrentMinTwentyfive OBJECT-TYPE
    SYNTAX      DisplayString
    MAX-ACCESS  read-write
    STATUS      current
    DESCRIPTION
	"TThe Min. current alarm value of output twenty five of master"
    ::= { masterOutputCurrentMin 25}
	
masterOutputCurrentMinTwentysix OBJECT-TYPE
    SYNTAX      DisplayString
    MAX-ACCESS  read-write
    STATUS      current
    DESCRIPTION
	"TThe Min. current alarm value of output twenty six of master"
    ::= { masterOutputCurrentMin 26}
	
masterOutputCurrentMinTwentyseven OBJECT-TYPE
    SYNTAX      DisplayString
    MAX-ACCESS  read-write
    STATUS      current
    DESCRIPTION
	"TThe Min. current alarm value of output twenty seven of master"
    ::= { masterOutputCurrentMin 27}
	
masterOutputCurrentMinTwentyeight OBJECT-TYPE
    SYNTAX      DisplayString
    MAX-ACCESS  read-write
    STATUS      current
    DESCRIPTION
	"TThe Min. current alarm value of output twenty eight of master"
    ::= { masterOutputCurrentMin 28}	
masterOutputCurrentMinTwentynine OBJECT-TYPE
    SYNTAX      DisplayString
    MAX-ACCESS  read-write
    STATUS      current
    DESCRIPTION
	"TThe Min. current alarm value of output twenty nine of master"
    ::= { masterOutputCurrentMin 29}
	
masterOutputCurrentMinThirty OBJECT-TYPE
    SYNTAX      DisplayString
    MAX-ACCESS  read-write
    STATUS      current
    DESCRIPTION
	"TThe Min. current alarm value of output thirty of master"
    ::= { masterOutputCurrentMin 30}
	
masterOutputCurrentMinThirtyone OBJECT-TYPE
    SYNTAX      DisplayString
    MAX-ACCESS  read-write
    STATUS      current
    DESCRIPTION
	"TThe Min. current alarm value of output thirty one of master"
    ::= { masterOutputCurrentMin 31}
	
masterOutputCurrentMinThirtytwo OBJECT-TYPE
    SYNTAX      DisplayString
    MAX-ACCESS  read-write
    STATUS      current
    DESCRIPTION
	"TThe Min. current alarm value of output thirty two of master"
    ::= { masterOutputCurrentMin 32}
	
masterOutputCurrentMinThirtythree OBJECT-TYPE
    SYNTAX      DisplayString
    MAX-ACCESS  read-write
    STATUS      current
    DESCRIPTION
	"TThe Min. current alarm value of output thirty three of master"
    ::= { masterOutputCurrentMin 33}
	
masterOutputCurrentMinThirtyfour OBJECT-TYPE
    SYNTAX      DisplayString
    MAX-ACCESS  read-write
    STATUS      current
    DESCRIPTION
	"TThe Min. current alarm value of output thirty four of master"
    ::= { masterOutputCurrentMin 34}
	
masterOutputCurrentMinThirtyfive OBJECT-TYPE
    SYNTAX      DisplayString
    MAX-ACCESS  read-write
    STATUS      current
    DESCRIPTION
	"TThe Min. current alarm value of output thirty five of master"
    ::= { masterOutputCurrentMin 35}
	
masterOutputCurrentMinThirtysix OBJECT-TYPE
    SYNTAX      DisplayString
    MAX-ACCESS  read-write
    STATUS      current
    DESCRIPTION
	"TThe Min. current alarm value of output thirty six of master"
    ::= { masterOutputCurrentMin 36}
	
masterOutputCurrentMinThirtyseven OBJECT-TYPE
    SYNTAX      DisplayString
    MAX-ACCESS  read-write
    STATUS      current
    DESCRIPTION
	"TThe Min. current alarm value of output thirty seven of master"
    ::= { masterOutputCurrentMin 37}
	
masterOutputCurrentMinThirtyeight OBJECT-TYPE
    SYNTAX      DisplayString
    MAX-ACCESS  read-write
    STATUS      current
    DESCRIPTION
	"TThe Min. current alarm value of output thirty eight of master"
    ::= { masterOutputCurrentMin 38}
	
masterOutputCurrentMinThirtynine OBJECT-TYPE
    SYNTAX      DisplayString
    MAX-ACCESS  read-write
    STATUS      current
    DESCRIPTION
	"TThe Min. current alarm value of output thirty nine of master"
    ::= { masterOutputCurrentMin 39}
	
masterOutputCurrentMinFourty OBJECT-TYPE
    SYNTAX      DisplayString
    MAX-ACCESS  read-write
    STATUS      current
    DESCRIPTION
	"TThe Min. current alarm value of output fourty of master"
    ::= { masterOutputCurrentMin 40}
	
masterOutputCurrentMinFourtyone OBJECT-TYPE
    SYNTAX      DisplayString
    MAX-ACCESS  read-write
    STATUS      current
    DESCRIPTION
	"TThe Min. current alarm value of output fourty one of master"
    ::= { masterOutputCurrentMin 41}
	
masterOutputCurrentMinFourtytwo OBJECT-TYPE
    SYNTAX      DisplayString
    MAX-ACCESS  read-write
    STATUS      current
    DESCRIPTION
	"TThe Min. current alarm value of output fourty two of master"
    ::= { masterOutputCurrentMin 42}


------------------------master output current Min critical----------------			
masterOutputCurrentMinCritical OBJECT IDENTIFIER ::= { masterOutputCurrent 3}	

masterOutputCurrentMinCriticalOne OBJECT-TYPE
    SYNTAX      DisplayString
    MAX-ACCESS  read-write
    STATUS      current
    DESCRIPTION
	"The first output Min. current warning value of master"
    ::= { masterOutputCurrentMinCritical 1}

masterOutputCurrentMinCriticalTwo OBJECT-TYPE
    SYNTAX      DisplayString
    MAX-ACCESS  read-write
    STATUS      current
    DESCRIPTION
	"The second output Min. current warning value of master"
    ::= { masterOutputCurrentMinCritical 2}

masterOutputCurrentMinCriticalThree OBJECT-TYPE
    SYNTAX      DisplayString
    MAX-ACCESS  read-write
    STATUS      current
    DESCRIPTION
	"The second output Min. current warning value of master"
    ::= { masterOutputCurrentMinCritical 3}

masterOutputCurrentMinCriticalFour OBJECT-TYPE
    SYNTAX      DisplayString
    MAX-ACCESS  read-write
    STATUS      current
    DESCRIPTION
	"The second output Min. current warning value of master"
    ::= { masterOutputCurrentMinCritical 4}

masterOutputCurrentMinCriticalFive OBJECT-TYPE
    SYNTAX      DisplayString
    MAX-ACCESS  read-write
    STATUS      current
    DESCRIPTION
	"The second output Min. current warning value of master"
    ::= { masterOutputCurrentMinCritical 5}

masterOutputCurrentMinCriticalSix OBJECT-TYPE
    SYNTAX      DisplayString
    MAX-ACCESS  read-write
    STATUS      current
    DESCRIPTION
	"The second output Min. current warning value of master"
    ::= { masterOutputCurrentMinCritical 6}

masterOutputCurrentMinCriticalSeven OBJECT-TYPE
    SYNTAX      DisplayString
    MAX-ACCESS  read-write
    STATUS      current
    DESCRIPTION
	"The second output Min. current warning value of master"
    ::= { masterOutputCurrentMinCritical 7}

masterOutputCurrentMinCriticalEight OBJECT-TYPE
    SYNTAX      DisplayString
    MAX-ACCESS  read-write
    STATUS      current
    DESCRIPTION
	"The second output Min. current warning value of master"
    ::= { masterOutputCurrentMinCritical 8}

masterOutputCurrentMinCriticalNine OBJECT-TYPE
    SYNTAX      DisplayString
    MAX-ACCESS  read-write
    STATUS      current
    DESCRIPTION
	"The second output Min. current warning value of master"
    ::= { masterOutputCurrentMinCritical 9}

masterOutputCurrentMinCriticalTen OBJECT-TYPE
    SYNTAX      DisplayString
    MAX-ACCESS  read-write
    STATUS      current
    DESCRIPTION
	"The second output Min. current warning value of master"
    ::= { masterOutputCurrentMinCritical 10}

masterOutputCurrentMinCriticalEleven OBJECT-TYPE
    SYNTAX      DisplayString
    MAX-ACCESS  read-write
    STATUS      current
    DESCRIPTION
	"The second output Min. current warning value of master"
    ::= { masterOutputCurrentMinCritical 11}

masterOutputCurrentMinCriticalTwel OBJECT-TYPE
    SYNTAX      DisplayString
    MAX-ACCESS  read-write
    STATUS      current
    DESCRIPTION
	"The second output Min. current warning value of master"
    ::= { masterOutputCurrentMinCritical 12}

masterOutputCurrentMinCriticalThirteen OBJECT-TYPE
    SYNTAX      DisplayString
    MAX-ACCESS  read-write
    STATUS      current
    DESCRIPTION
	"The second output Min. current warning value of master"
    ::= { masterOutputCurrentMinCritical 13}

masterOutputCurrentMinCriticalFourteen OBJECT-TYPE
    SYNTAX      DisplayString
    MAX-ACCESS  read-write
    STATUS      current
    DESCRIPTION
	"The second output Min. current warning value of master"
    ::= { masterOutputCurrentMinCritical 14}

masterOutputCurrentMinCriticalFifteen OBJECT-TYPE
    SYNTAX      DisplayString
    MAX-ACCESS  read-write
    STATUS      current
    DESCRIPTION
	"The second output Min. current warning value of master"
    ::= { masterOutputCurrentMinCritical 15}

masterOutputCurrentMinCriticalSixteen OBJECT-TYPE
    SYNTAX      DisplayString
    MAX-ACCESS  read-write
    STATUS      current
    DESCRIPTION
	"The second output Min. current warning value of master"
    ::= { masterOutputCurrentMinCritical 16}

masterOutputCurrentMinCriticalSeventeen OBJECT-TYPE
    SYNTAX      DisplayString
    MAX-ACCESS  read-write
    STATUS      current
    DESCRIPTION
	"The second output Min. current warning value of master"
    ::= { masterOutputCurrentMinCritical 17}

masterOutputCurrentMinCriticalEighteen OBJECT-TYPE
    SYNTAX      DisplayString
    MAX-ACCESS  read-write
    STATUS      current
    DESCRIPTION
	"The second output Min. current warning value of master"
    ::= { masterOutputCurrentMinCritical 18}
	
masterOutputCurrentMinCriticalNineteen OBJECT-TYPE
    SYNTAX      DisplayString
    MAX-ACCESS  read-write
    STATUS      current
    DESCRIPTION
	"The second output Min. current warning value of master"
    ::= { masterOutputCurrentMinCritical 19}
	
masterOutputCurrentMinCriticaltwenty OBJECT-TYPE
    SYNTAX      DisplayString
    MAX-ACCESS  read-write
    STATUS      current
    DESCRIPTION
	"The second output Min. current warning value of master"
    ::= { masterOutputCurrentMinCritical 20}
	
masterOutputCurrentMinCriticalTwentyone OBJECT-TYPE
    SYNTAX      DisplayString
    MAX-ACCESS  read-write
    STATUS      current
    DESCRIPTION
	"The second output Min. current warning value of master"
    ::= { masterOutputCurrentMinCritical 21}
	
masterOutputCurrentMinCriticalTwentyonetwo OBJECT-TYPE
    SYNTAX      DisplayString
    MAX-ACCESS  read-write
    STATUS      current
    DESCRIPTION
	"The second output Min. current warning value of master"
    ::= { masterOutputCurrentMinCritical 22}
	
masterOutputCurrentMinCriticalTwentythree OBJECT-TYPE
    SYNTAX      DisplayString
    MAX-ACCESS  read-write
    STATUS      current
    DESCRIPTION
	"The second output Min. current warning value of master"
    ::= { masterOutputCurrentMinCritical 23}
	
masterOutputCurrentMinCriticalTwentyfour OBJECT-TYPE
    SYNTAX      DisplayString
    MAX-ACCESS  read-write
    STATUS      current
    DESCRIPTION
	"The second output Min. current warning value of master"
    ::= { masterOutputCurrentMinCritical 24}
	
masterOutputCurrentMinCriticalTwentyfive OBJECT-TYPE
    SYNTAX      DisplayString
    MAX-ACCESS  read-write
    STATUS      current
    DESCRIPTION
	"The second output Min. current warning value of master"
    ::= { masterOutputCurrentMinCritical 25}
	
masterOutputCurrentMinCriticalTwentysix OBJECT-TYPE
    SYNTAX      DisplayString
    MAX-ACCESS  read-write
    STATUS      current
    DESCRIPTION
	"The second output Min. current warning value of master"
    ::= { masterOutputCurrentMinCritical 26}
	
masterOutputCurrentMinCriticalTwentyseven OBJECT-TYPE
    SYNTAX      DisplayString
    MAX-ACCESS  read-write
    STATUS      current
    DESCRIPTION
	"The second output Min. current warning value of master"
    ::= { masterOutputCurrentMinCritical 27}
	
masterOutputCurrentMinCriticalTwentyeight OBJECT-TYPE
    SYNTAX      DisplayString
    MAX-ACCESS  read-write
    STATUS      current
    DESCRIPTION
	"The second output Min. current warning value of master"
    ::= { masterOutputCurrentMinCritical 28}	
masterOutputCurrentMinCriticalTwentynine OBJECT-TYPE
    SYNTAX      DisplayString
    MAX-ACCESS  read-write
    STATUS      current
    DESCRIPTION
	"The second output Min. current warning value of master"
    ::= { masterOutputCurrentMinCritical 29}
	
masterOutputCurrentMinCriticalThirty OBJECT-TYPE
    SYNTAX      DisplayString
    MAX-ACCESS  read-write
    STATUS      current
    DESCRIPTION
	"The second output Min. current warning value of master"
    ::= { masterOutputCurrentMinCritical 30}
	
masterOutputCurrentMinCriticalThirtyone OBJECT-TYPE
    SYNTAX      DisplayString
    MAX-ACCESS  read-write
    STATUS      current
    DESCRIPTION
	"The second output Min. current warning value of master"
    ::= { masterOutputCurrentMinCritical 31}
	
masterOutputCurrentMinCriticalThirtytwo OBJECT-TYPE
    SYNTAX      DisplayString
    MAX-ACCESS  read-write
    STATUS      current
    DESCRIPTION
	"The second output Min. current warning value of master"
    ::= { masterOutputCurrentMinCritical 32}
	
masterOutputCurrentMinCriticalThirtythree OBJECT-TYPE
    SYNTAX      DisplayString
    MAX-ACCESS  read-write
    STATUS      current
    DESCRIPTION
	"The second output Min. current warning value of master"
    ::= { masterOutputCurrentMinCritical 33}
	
masterOutputCurrentMinCriticalThirtyfour OBJECT-TYPE
    SYNTAX      DisplayString
    MAX-ACCESS  read-write
    STATUS      current
    DESCRIPTION
	"The second output Min. current warning value of master"
    ::= { masterOutputCurrentMinCritical 34}
	
masterOutputCurrentMinCriticalThirtyfive OBJECT-TYPE
    SYNTAX      DisplayString
    MAX-ACCESS  read-write
    STATUS      current
    DESCRIPTION
	"The second output Min. current warning value of master"
    ::= { masterOutputCurrentMinCritical 35}
	
masterOutputCurrentMinCriticalThirtysix OBJECT-TYPE
    SYNTAX      DisplayString
    MAX-ACCESS  read-write
    STATUS      current
    DESCRIPTION
	"The second output Min. current warning value of master"
    ::= { masterOutputCurrentMinCritical 36}
	
masterOutputCurrentMinCriticalThirtyseven OBJECT-TYPE
    SYNTAX      DisplayString
    MAX-ACCESS  read-write
    STATUS      current
    DESCRIPTION
	"The second output Min. current warning value of master"
    ::= { masterOutputCurrentMinCritical 37}
	
masterOutputCurrentMinCriticalThirtyeight OBJECT-TYPE
    SYNTAX      DisplayString
    MAX-ACCESS  read-write
    STATUS      current
    DESCRIPTION
	"The second output Min. current warning value of master"
    ::= { masterOutputCurrentMinCritical 38}
	
masterOutputCurrentMinCriticalThirtynine OBJECT-TYPE
    SYNTAX      DisplayString
    MAX-ACCESS  read-write
    STATUS      current
    DESCRIPTION
	"The second output Min. current warning value of master"
    ::= { masterOutputCurrentMinCritical 39}
	
masterOutputCurrentMinCriticalFourty OBJECT-TYPE
    SYNTAX      DisplayString
    MAX-ACCESS  read-write
    STATUS      current
    DESCRIPTION
	"The second output Min. current warning value of master"
    ::= { masterOutputCurrentMinCritical 40}
	
masterOutputCurrentMinCriticalFourtyone OBJECT-TYPE
    SYNTAX      DisplayString
    MAX-ACCESS  read-write
    STATUS      current
    DESCRIPTION
	"The second output Min. current warning value of master"
    ::= { masterOutputCurrentMinCritical 41}
	
masterOutputCurrentMinCriticalFourtytwo OBJECT-TYPE
    SYNTAX      DisplayString
    MAX-ACCESS  read-write
    STATUS      current
    DESCRIPTION
	"The second output Min. current warning value of master"
    ::= { masterOutputCurrentMinCritical 42}
	
	
------------------------master output current Max critical----------------			
masterOutputCurrentMaxCritical OBJECT IDENTIFIER ::= { masterOutputCurrent 4}	

masterOutputCurrentMaxCriticalOne OBJECT-TYPE
    SYNTAX      DisplayString
    MAX-ACCESS  read-write
    STATUS      current
    DESCRIPTION
	"The first output Max. current warning value of master"
    ::= { masterOutputCurrentMaxCritical 1}

masterOutputCurrentMaxCriticalTwo OBJECT-TYPE
    SYNTAX      DisplayString
    MAX-ACCESS  read-write
    STATUS      current
    DESCRIPTION
	"The second output Max. current warning value of master"
    ::= { masterOutputCurrentMaxCritical 2}

masterOutputCurrentMaxCriticalThree OBJECT-TYPE
    SYNTAX      DisplayString
    MAX-ACCESS  read-write
    STATUS      current
    DESCRIPTION
	"The second output Max. current warning value of master"
    ::= { masterOutputCurrentMaxCritical 3}

masterOutputCurrentMaxCriticalFour OBJECT-TYPE
    SYNTAX      DisplayString
    MAX-ACCESS  read-write
    STATUS      current
    DESCRIPTION
	"The second output Max. current warning value of master"
    ::= { masterOutputCurrentMaxCritical 4}

masterOutputCurrentMaxCriticalFive OBJECT-TYPE
    SYNTAX      DisplayString
    MAX-ACCESS  read-write
    STATUS      current
    DESCRIPTION
	"The second output Max. current warning value of master"
    ::= { masterOutputCurrentMaxCritical 5}

masterOutputCurrentMaxCriticalSix OBJECT-TYPE
    SYNTAX      DisplayString
    MAX-ACCESS  read-write
    STATUS      current
    DESCRIPTION
	"The second output Max. current warning value of master"
    ::= { masterOutputCurrentMaxCritical 6}

masterOutputCurrentMaxCriticalSeven OBJECT-TYPE
    SYNTAX      DisplayString
    MAX-ACCESS  read-write
    STATUS      current
    DESCRIPTION
	"The second output Max. current warning value of master"
    ::= { masterOutputCurrentMaxCritical 7}

masterOutputCurrentMaxCriticalEight OBJECT-TYPE
    SYNTAX      DisplayString
    MAX-ACCESS  read-write
    STATUS      current
    DESCRIPTION
	"The second output Max. current warning value of master"
    ::= { masterOutputCurrentMaxCritical 8}

masterOutputCurrentMaxCriticalNine OBJECT-TYPE
    SYNTAX      DisplayString
    MAX-ACCESS  read-write
    STATUS      current
    DESCRIPTION
	"The second output Max. current warning value of master"
    ::= { masterOutputCurrentMaxCritical 9}

masterOutputCurrentMaxCriticalTen OBJECT-TYPE
    SYNTAX      DisplayString
    MAX-ACCESS  read-write
    STATUS      current
    DESCRIPTION
	"The second output Max. current warning value of master"
    ::= { masterOutputCurrentMaxCritical 10}

masterOutputCurrentMaxCriticalEleven OBJECT-TYPE
    SYNTAX      DisplayString
    MAX-ACCESS  read-write
    STATUS      current
    DESCRIPTION
	"The second output Max. current warning value of master"
    ::= { masterOutputCurrentMaxCritical 11}

masterOutputCurrentMaxCriticalTwel OBJECT-TYPE
    SYNTAX      DisplayString
    MAX-ACCESS  read-write
    STATUS      current
    DESCRIPTION
	"The second output Max. current warning value of master"
    ::= { masterOutputCurrentMaxCritical 12}

masterOutputCurrentMaxCriticalThirteen OBJECT-TYPE
    SYNTAX      DisplayString
    MAX-ACCESS  read-write
    STATUS      current
    DESCRIPTION
	"The second output Max. current warning value of master"
    ::= { masterOutputCurrentMaxCritical 13}

masterOutputCurrentMaxCriticalFourteen OBJECT-TYPE
    SYNTAX      DisplayString
    MAX-ACCESS  read-write
    STATUS      current
    DESCRIPTION
	"The second output Max. current warning value of master"
    ::= { masterOutputCurrentMaxCritical 14}

masterOutputCurrentMaxCriticalFifteen OBJECT-TYPE
    SYNTAX      DisplayString
    MAX-ACCESS  read-write
    STATUS      current
    DESCRIPTION
	"The second output Max. current warning value of master"
    ::= { masterOutputCurrentMaxCritical 15}

masterOutputCurrentMaxCriticalSixteen OBJECT-TYPE
    SYNTAX      DisplayString
    MAX-ACCESS  read-write
    STATUS      current
    DESCRIPTION
	"The second output Max. current warning value of master"
    ::= { masterOutputCurrentMaxCritical 16}

masterOutputCurrentMaxCriticalSeventeen OBJECT-TYPE
    SYNTAX      DisplayString
    MAX-ACCESS  read-write
    STATUS      current
    DESCRIPTION
	"The second output Max. current warning value of master"
    ::= { masterOutputCurrentMaxCritical 17}

masterOutputCurrentMaxCriticalEighteen OBJECT-TYPE
    SYNTAX      DisplayString
    MAX-ACCESS  read-write
    STATUS      current
    DESCRIPTION
	"The second output Max. current warning value of master"
    ::= { masterOutputCurrentMaxCritical 18}
	
masterOutputCurrentMaxCriticalNineteen OBJECT-TYPE
    SYNTAX      DisplayString
    MAX-ACCESS  read-write
    STATUS      current
    DESCRIPTION
	"The second output Max. current warning value of master"
    ::= { masterOutputCurrentMaxCritical 19}
	
masterOutputCurrentMaxCriticaltwenty OBJECT-TYPE
    SYNTAX      DisplayString
    MAX-ACCESS  read-write
    STATUS      current
    DESCRIPTION
	"The second output Max. current warning value of master"
    ::= { masterOutputCurrentMaxCritical 20}
	
masterOutputCurrentMaxCriticalTwentyone OBJECT-TYPE
    SYNTAX      DisplayString
    MAX-ACCESS  read-write
    STATUS      current
    DESCRIPTION
	"The second output Max. current warning value of master"
    ::= { masterOutputCurrentMaxCritical 21}
	
masterOutputCurrentMaxCriticalTwentyonetwo OBJECT-TYPE
    SYNTAX      DisplayString
    MAX-ACCESS  read-write
    STATUS      current
    DESCRIPTION
	"The second output Max. current warning value of master"
    ::= { masterOutputCurrentMaxCritical 22}
	
masterOutputCurrentMaxCriticalTwentythree OBJECT-TYPE
    SYNTAX      DisplayString
    MAX-ACCESS  read-write
    STATUS      current
    DESCRIPTION
	"The second output Max. current warning value of master"
    ::= { masterOutputCurrentMaxCritical 23}
	
masterOutputCurrentMaxCriticalTwentyfour OBJECT-TYPE
    SYNTAX      DisplayString
    MAX-ACCESS  read-write
    STATUS      current
    DESCRIPTION
	"The second output Max. current warning value of master"
    ::= { masterOutputCurrentMaxCritical 24}
	
masterOutputCurrentMaxCriticalTwentyfive OBJECT-TYPE
    SYNTAX      DisplayString
    MAX-ACCESS  read-write
    STATUS      current
    DESCRIPTION
	"The second output Max. current warning value of master"
    ::= { masterOutputCurrentMaxCritical 25}
	
masterOutputCurrentMaxCriticalTwentysix OBJECT-TYPE
    SYNTAX      DisplayString
    MAX-ACCESS  read-write
    STATUS      current
    DESCRIPTION
	"The second output Max. current warning value of master"
    ::= { masterOutputCurrentMaxCritical 26}
	
masterOutputCurrentMaxCriticalTwentyseven OBJECT-TYPE
    SYNTAX      DisplayString
    MAX-ACCESS  read-write
    STATUS      current
    DESCRIPTION
	"The second output Max. current warning value of master"
    ::= { masterOutputCurrentMaxCritical 27}
	
masterOutputCurrentMaxCriticalTwentyeight OBJECT-TYPE
    SYNTAX      DisplayString
    MAX-ACCESS  read-write
    STATUS      current
    DESCRIPTION
	"The second output Max. current warning value of master"
    ::= { masterOutputCurrentMaxCritical 28}	
masterOutputCurrentMaxCriticalTwentynine OBJECT-TYPE
    SYNTAX      DisplayString
    MAX-ACCESS  read-write
    STATUS      current
    DESCRIPTION
	"The second output Max. current warning value of master"
    ::= { masterOutputCurrentMaxCritical 29}
	
masterOutputCurrentMaxCriticalThirty OBJECT-TYPE
    SYNTAX      DisplayString
    MAX-ACCESS  read-write
    STATUS      current
    DESCRIPTION
	"The second output Max. current warning value of master"
    ::= { masterOutputCurrentMaxCritical 30}
	
masterOutputCurrentMaxCriticalThirtyone OBJECT-TYPE
    SYNTAX      DisplayString
    MAX-ACCESS  read-write
    STATUS      current
    DESCRIPTION
	"The second output Max. current warning value of master"
    ::= { masterOutputCurrentMaxCritical 31}
	
masterOutputCurrentMaxCriticalThirtytwo OBJECT-TYPE
    SYNTAX      DisplayString
    MAX-ACCESS  read-write
    STATUS      current
    DESCRIPTION
	"The second output Max. current warning value of master"
    ::= { masterOutputCurrentMaxCritical 32}
	
masterOutputCurrentMaxCriticalThirtythree OBJECT-TYPE
    SYNTAX      DisplayString
    MAX-ACCESS  read-write
    STATUS      current
    DESCRIPTION
	"The second output Max. current warning value of master"
    ::= { masterOutputCurrentMaxCritical 33}
	
masterOutputCurrentMaxCriticalThirtyfour OBJECT-TYPE
    SYNTAX      DisplayString
    MAX-ACCESS  read-write
    STATUS      current
    DESCRIPTION
	"The second output Max. current warning value of master"
    ::= { masterOutputCurrentMaxCritical 34}
	
masterOutputCurrentMaxCriticalThirtyfive OBJECT-TYPE
    SYNTAX      DisplayString
    MAX-ACCESS  read-write
    STATUS      current
    DESCRIPTION
	"The second output Max. current warning value of master"
    ::= { masterOutputCurrentMaxCritical 35}
	
masterOutputCurrentMaxCriticalThirtysix OBJECT-TYPE
    SYNTAX      DisplayString
    MAX-ACCESS  read-write
    STATUS      current
    DESCRIPTION
	"The second output Max. current warning value of master"
    ::= { masterOutputCurrentMaxCritical 36}
	
masterOutputCurrentMaxCriticalThirtyseven OBJECT-TYPE
    SYNTAX      DisplayString
    MAX-ACCESS  read-write
    STATUS      current
    DESCRIPTION
	"The second output Max. current warning value of master"
    ::= { masterOutputCurrentMaxCritical 37}
	
masterOutputCurrentMaxCriticalThirtyeight OBJECT-TYPE
    SYNTAX      DisplayString
    MAX-ACCESS  read-write
    STATUS      current
    DESCRIPTION
	"The second output Max. current warning value of master"
    ::= { masterOutputCurrentMaxCritical 38}
	
masterOutputCurrentMaxCriticalThirtynine OBJECT-TYPE
    SYNTAX      DisplayString
    MAX-ACCESS  read-write
    STATUS      current
    DESCRIPTION
	"The second output Max. current warning value of master"
    ::= { masterOutputCurrentMaxCritical 39}
	
masterOutputCurrentMaxCriticalFourty OBJECT-TYPE
    SYNTAX      DisplayString
    MAX-ACCESS  read-write
    STATUS      current
    DESCRIPTION
	"The second output Max. current warning value of master"
    ::= { masterOutputCurrentMaxCritical 40}
	
masterOutputCurrentMaxCriticalFourtyone OBJECT-TYPE
    SYNTAX      DisplayString
    MAX-ACCESS  read-write
    STATUS      current
    DESCRIPTION
	"The second output Max. current warning value of master"
    ::= { masterOutputCurrentMaxCritical 41}
	
masterOutputCurrentMaxCriticalFourtytwo OBJECT-TYPE
    SYNTAX      DisplayString
    MAX-ACCESS  read-write
    STATUS      current
    DESCRIPTION
	"The second output Max. current warning value of master"
    ::= { masterOutputCurrentMaxCritical 42}
	
	
------------------------master output current Max----------------			
masterOutputCurrentMax OBJECT IDENTIFIER ::= { masterOutputCurrent 5}
	
masterOutputCurrentMaxOne OBJECT-TYPE
    SYNTAX      DisplayString
    MAX-ACCESS  read-write
    STATUS      current
    DESCRIPTION
	"The first output Max. current alarm value of master"
    ::= { masterOutputCurrentMax 1}

masterOutputCurrentMaxTwo OBJECT-TYPE
    SYNTAX      DisplayString
    MAX-ACCESS  read-write
    STATUS      current
    DESCRIPTION
	"The second output Max. current alarm value of master"
    ::= { masterOutputCurrentMax 2}

masterOutputCurrentMaxThree OBJECT-TYPE
    SYNTAX      DisplayString
    MAX-ACCESS  read-write
    STATUS      current
    DESCRIPTION
	"The second output Max. current alarm value of master"
    ::= { masterOutputCurrentMax 3}

masterOutputCurrentMaxFour OBJECT-TYPE
    SYNTAX      DisplayString
    MAX-ACCESS  read-write
    STATUS      current
    DESCRIPTION
	"The second output Max. current alarm value of master"
    ::= { masterOutputCurrentMax 4}

masterOutputCurrentMaxFive OBJECT-TYPE
    SYNTAX      DisplayString
    MAX-ACCESS  read-write
    STATUS      current
    DESCRIPTION
	"The second output Max. current alarm value of master"
    ::= { masterOutputCurrentMax 5}

masterOutputCurrentMaxSix OBJECT-TYPE
    SYNTAX      DisplayString
    MAX-ACCESS  read-write
    STATUS      current
    DESCRIPTION
	"The second output Max. current alarm value of master"
    ::= { masterOutputCurrentMax 6}

masterOutputCurrentMaxSeven OBJECT-TYPE
    SYNTAX      DisplayString
    MAX-ACCESS  read-write
    STATUS      current
    DESCRIPTION
	"The second output Max. current alarm value of master"
    ::= { masterOutputCurrentMax 7}

masterOutputCurrentMaxEight OBJECT-TYPE
    SYNTAX      DisplayString
    MAX-ACCESS  read-write
    STATUS      current
    DESCRIPTION
	"The second output Max. current alarm value of master"
    ::= { masterOutputCurrentMax 8}

masterOutputCurrentMaxNine OBJECT-TYPE
    SYNTAX      DisplayString
    MAX-ACCESS  read-write
    STATUS      current
    DESCRIPTION
	"The second output Max. current alarm value of master"
    ::= { masterOutputCurrentMax 9}

masterOutputCurrentMaxTen OBJECT-TYPE
    SYNTAX      DisplayString
    MAX-ACCESS  read-write
    STATUS      current
    DESCRIPTION
	"The second output Max. current alarm value of master"
    ::= { masterOutputCurrentMax 10}

masterOutputCurrentMaxEleven OBJECT-TYPE
    SYNTAX      DisplayString
    MAX-ACCESS  read-write
    STATUS      current
    DESCRIPTION
	"The second output Max. current alarm value of master"
    ::= { masterOutputCurrentMax 11}

masterOutputCurrentMaxTwel OBJECT-TYPE
    SYNTAX      DisplayString
    MAX-ACCESS  read-write
    STATUS      current
    DESCRIPTION
	"The second output Max. current alarm value of master"
    ::= { masterOutputCurrentMax 12}

masterOutputCurrentMaxThirteen OBJECT-TYPE
    SYNTAX      DisplayString
    MAX-ACCESS  read-write
    STATUS      current
    DESCRIPTION
	"The second output Max. current alarm value of master"
    ::= { masterOutputCurrentMax 13}

masterOutputCurrentMaxFourteen OBJECT-TYPE
    SYNTAX      DisplayString
    MAX-ACCESS  read-write
    STATUS      current
    DESCRIPTION
	"The second output Max. current alarm value of master"
    ::= { masterOutputCurrentMax 14}

masterOutputCurrentMaxFifteen OBJECT-TYPE
    SYNTAX      DisplayString
    MAX-ACCESS  read-write
    STATUS      current
    DESCRIPTION
	"The second output Max. current alarm value of master"
    ::= { masterOutputCurrentMax 15}

masterOutputCurrentMaxSixteen OBJECT-TYPE
    SYNTAX      DisplayString
    MAX-ACCESS  read-write
    STATUS      current
    DESCRIPTION
	"The second output Max. current alarm value of master"
    ::= { masterOutputCurrentMax 16}

masterOutputCurrentMaxSeventeen OBJECT-TYPE
    SYNTAX      DisplayString
    MAX-ACCESS  read-write
    STATUS      current
    DESCRIPTION
	"The second output Max. current alarm value of master"
    ::= { masterOutputCurrentMax 17}

masterOutputCurrentMaxEighteen OBJECT-TYPE
    SYNTAX      DisplayString
    MAX-ACCESS  read-write
    STATUS      current
    DESCRIPTION
	"The second output Max. current alarm value of master"
    ::= { masterOutputCurrentMax 18}
	
masterOutputCurrentMaxNineteen OBJECT-TYPE
    SYNTAX      DisplayString
    MAX-ACCESS  read-write
    STATUS      current
    DESCRIPTION
	"The second output Max. current alarm value of master"
    ::= { masterOutputCurrentMax 19}
	
masterOutputCurrentMaxtwenty OBJECT-TYPE
    SYNTAX      DisplayString
    MAX-ACCESS  read-write
    STATUS      current
    DESCRIPTION
	"The second output Max. current alarm value of master"
    ::= { masterOutputCurrentMax 20}
	
masterOutputCurrentMaxTwentyone OBJECT-TYPE
    SYNTAX      DisplayString
    MAX-ACCESS  read-write
    STATUS      current
    DESCRIPTION
	"The second output Max. current alarm value of master"
    ::= { masterOutputCurrentMax 21}
	
masterOutputCurrentMaxTwentyonetwo OBJECT-TYPE
    SYNTAX      DisplayString
    MAX-ACCESS  read-write
    STATUS      current
    DESCRIPTION
	"The second output Max. current alarm value of master"
    ::= { masterOutputCurrentMax 22}
	
masterOutputCurrentMaxTwentythree OBJECT-TYPE
    SYNTAX      DisplayString
    MAX-ACCESS  read-write
    STATUS      current
    DESCRIPTION
	"The second output Max. current alarm value of master"
    ::= { masterOutputCurrentMax 23}
	
masterOutputCurrentMaxTwentyfour OBJECT-TYPE
    SYNTAX      DisplayString
    MAX-ACCESS  read-write
    STATUS      current
    DESCRIPTION
	"The second output Max. current alarm value of master"
    ::= { masterOutputCurrentMax 24}
	
masterOutputCurrentMaxTwentyfive OBJECT-TYPE
    SYNTAX      DisplayString
    MAX-ACCESS  read-write
    STATUS      current
    DESCRIPTION
	"The second output Max. current alarm value of master"
    ::= { masterOutputCurrentMax 25}
	
masterOutputCurrentMaxTwentysix OBJECT-TYPE
    SYNTAX      DisplayString
    MAX-ACCESS  read-write
    STATUS      current
    DESCRIPTION
	"The second output Max. current alarm value of master"
    ::= { masterOutputCurrentMax 26}
	
masterOutputCurrentMaxTwentyseven OBJECT-TYPE
    SYNTAX      DisplayString
    MAX-ACCESS  read-write
    STATUS      current
    DESCRIPTION
	"The second output Max. current alarm value of master"
    ::= { masterOutputCurrentMax 27}
	
masterOutputCurrentMaxTwentyeight OBJECT-TYPE
    SYNTAX      DisplayString
    MAX-ACCESS  read-write
    STATUS      current
    DESCRIPTION
	"The second output Max. current alarm value of master"
    ::= { masterOutputCurrentMax 28}	
masterOutputCurrentMaxTwentynine OBJECT-TYPE
    SYNTAX      DisplayString
    MAX-ACCESS  read-write
    STATUS      current
    DESCRIPTION
	"The second output Max. current alarm value of master"
    ::= { masterOutputCurrentMax 29}
	
masterOutputCurrentMaxThirty OBJECT-TYPE
    SYNTAX      DisplayString
    MAX-ACCESS  read-write
    STATUS      current
    DESCRIPTION
	"The second output Max. current alarm value of master"
    ::= { masterOutputCurrentMax 30}
	
masterOutputCurrentMaxThirtyone OBJECT-TYPE
    SYNTAX      DisplayString
    MAX-ACCESS  read-write
    STATUS      current
    DESCRIPTION
	"The second output Max. current alarm value of master"
    ::= { masterOutputCurrentMax 31}
	
masterOutputCurrentMaxThirtytwo OBJECT-TYPE
    SYNTAX      DisplayString
    MAX-ACCESS  read-write
    STATUS      current
    DESCRIPTION
	"The second output Max. current alarm value of master"
    ::= { masterOutputCurrentMax 32}
	
masterOutputCurrentMaxThirtythree OBJECT-TYPE
    SYNTAX      DisplayString
    MAX-ACCESS  read-write
    STATUS      current
    DESCRIPTION
	"The second output Max. current alarm value of master"
    ::= { masterOutputCurrentMax 33}
	
masterOutputCurrentMaxThirtyfour OBJECT-TYPE
    SYNTAX      DisplayString
    MAX-ACCESS  read-write
    STATUS      current
    DESCRIPTION
	"The second output Max. current alarm value of master"
    ::= { masterOutputCurrentMax 34}
	
masterOutputCurrentMaxThirtyfive OBJECT-TYPE
    SYNTAX      DisplayString
    MAX-ACCESS  read-write
    STATUS      current
    DESCRIPTION
	"The second output Max. current alarm value of master"
    ::= { masterOutputCurrentMax 35}
	
masterOutputCurrentMaxThirtysix OBJECT-TYPE
    SYNTAX      DisplayString
    MAX-ACCESS  read-write
    STATUS      current
    DESCRIPTION
	"The second output Max. current alarm value of master"
    ::= { masterOutputCurrentMax 36}
	
masterOutputCurrentMaxThirtyseven OBJECT-TYPE
    SYNTAX      DisplayString
    MAX-ACCESS  read-write
    STATUS      current
    DESCRIPTION
	"The second output Max. current alarm value of master"
    ::= { masterOutputCurrentMax 37}
	
masterOutputCurrentMaxThirtyeight OBJECT-TYPE
    SYNTAX      DisplayString
    MAX-ACCESS  read-write
    STATUS      current
    DESCRIPTION
	"The second output Max. current alarm value of master"
    ::= { masterOutputCurrentMax 38}
	
masterOutputCurrentMaxThirtynine OBJECT-TYPE
    SYNTAX      DisplayString
    MAX-ACCESS  read-write
    STATUS      current
    DESCRIPTION
	"The second output Max. current alarm value of master"
    ::= { masterOutputCurrentMax 39}
	
masterOutputCurrentMaxFourty OBJECT-TYPE
    SYNTAX      DisplayString
    MAX-ACCESS  read-write
    STATUS      current
    DESCRIPTION
	"The second output Max. current alarm value of master"
    ::= { masterOutputCurrentMax 40}
	
masterOutputCurrentMaxFourtyone OBJECT-TYPE
    SYNTAX      DisplayString
    MAX-ACCESS  read-write
    STATUS      current
    DESCRIPTION
	"The second output Max. current alarm value of master"
    ::= { masterOutputCurrentMax 41}
	
masterOutputCurrentMaxFourtytwo OBJECT-TYPE
    SYNTAX      DisplayString
    MAX-ACCESS  read-write
    STATUS      current
    DESCRIPTION
	"The second output Max. current alarm value of master"
    ::= { masterOutputCurrentMax 42}
	
	
-------------------------------master output powerfactor------------------------	
masterOutputPowerfactor OBJECT IDENTIFIER ::= { master 9}	

masterOutputPowerfactorOne OBJECT-TYPE
    SYNTAX      DisplayString
    MAX-ACCESS  read-only
    STATUS      current
    DESCRIPTION
	"The ouput power factor of master." 
	::= { masterOutputPowerfactor 1}

masterOutputPowerfactorTwo OBJECT-TYPE
    SYNTAX      DisplayString
    MAX-ACCESS  read-only
    STATUS      current
    DESCRIPTION
	"The ouput power factor of master." 
	::= { masterOutputPowerfactor 2}
	
masterOutputPowerfactorThree OBJECT-TYPE
    SYNTAX      DisplayString
    MAX-ACCESS  read-only
    STATUS      current
    DESCRIPTION
	"The ouput power factor of master." 
	::= { masterOutputPowerfactor 3}
	
masterOutputPowerfactorFour OBJECT-TYPE
    SYNTAX      DisplayString
    MAX-ACCESS  read-only
    STATUS      current
    DESCRIPTION
	"The ouput power factor of master." 
	::= { masterOutputPowerfactor 4}
		
masterOutputPowerfactorFive OBJECT-TYPE
    SYNTAX      DisplayString
    MAX-ACCESS  read-only
    STATUS      current
    DESCRIPTION
	"The ouput power factor of master." 
	::= { masterOutputPowerfactor 5}
	
masterOutputPowerfactorSix OBJECT-TYPE
    SYNTAX      DisplayString
    MAX-ACCESS  read-only
    STATUS      current
    DESCRIPTION
	"The ouput power factor of master." 
	::= { masterOutputPowerfactor 6}
	
masterOutputPowerfactorSeven OBJECT-TYPE
    SYNTAX      DisplayString
    MAX-ACCESS  read-only
    STATUS      current
    DESCRIPTION
	"The ouput power factor of master." 
	::= { masterOutputPowerfactor 7}	
	
masterOutputPowerfactorEight OBJECT-TYPE
    SYNTAX      DisplayString
    MAX-ACCESS  read-only
    STATUS      current
    DESCRIPTION
	"The ouput power factor of master." 
	::= { masterOutputPowerfactor 8}
	
masterOutputPowerfactorNine OBJECT-TYPE
    SYNTAX      DisplayString
    MAX-ACCESS  read-only
    STATUS      current
    DESCRIPTION
	"The ouput power factor of master." 
	::= { masterOutputPowerfactor 9}
		
masterOutputPowerfactorTen OBJECT-TYPE
    SYNTAX      DisplayString
    MAX-ACCESS  read-only
    STATUS      current
    DESCRIPTION
	"The ouput power factor of master." 
	::= { masterOutputPowerfactor 10}
		
masterOutputPowerfactorEleven OBJECT-TYPE
    SYNTAX      DisplayString
    MAX-ACCESS  read-only
    STATUS      current
    DESCRIPTION
	"The ouput power factor of master." 
	::= { masterOutputPowerfactor 11}
		
masterOutputPowerfactorTwel OBJECT-TYPE
    SYNTAX      DisplayString
    MAX-ACCESS  read-only
    STATUS      current
    DESCRIPTION
	"The ouput power factor of master." 
	::= { masterOutputPowerfactor 12}
		
masterOutputPowerfactorThirteen OBJECT-TYPE
    SYNTAX      DisplayString
    MAX-ACCESS  read-only
    STATUS      current
    DESCRIPTION
	"The ouput power factor of master." 
	::= { masterOutputPowerfactor 13}
		
masterOutputPowerfactorFourteen OBJECT-TYPE
    SYNTAX      DisplayString
    MAX-ACCESS  read-only
    STATUS      current
    DESCRIPTION
	"The ouput power factor of master." 
	::= { masterOutputPowerfactor 14}
		
masterOutputPowerfactorFifteen OBJECT-TYPE
    SYNTAX      DisplayString
    MAX-ACCESS  read-only
    STATUS      current
    DESCRIPTION
	"The ouput power factor of master." 
	::= { masterOutputPowerfactor 15}
		
masterOutputPowerfactorSixteen OBJECT-TYPE
    SYNTAX      DisplayString
    MAX-ACCESS  read-only
    STATUS      current
    DESCRIPTION
	"The ouput power factor of master." 
	::= { masterOutputPowerfactor 16}
		
masterOutputPowerfactorSeventeen OBJECT-TYPE
    SYNTAX      DisplayString
    MAX-ACCESS  read-only
    STATUS      current
    DESCRIPTION
	"The ouput power factor of master." 
	::= { masterOutputPowerfactor 17}
		
masterOutputPowerfactorEighteen OBJECT-TYPE
    SYNTAX      DisplayString
    MAX-ACCESS  read-only
    STATUS      current
    DESCRIPTION
	"The ouput power factor of master." 
	::= { masterOutputPowerfactor 18}
		
masterOutputPowerfactorNineteen OBJECT-TYPE
    SYNTAX      DisplayString
    MAX-ACCESS  read-only
    STATUS      current
    DESCRIPTION
	"The ouput power factor of master." 
	::= { masterOutputPowerfactor 19}
		
masterOutputPowerfactorTwenty OBJECT-TYPE
    SYNTAX      DisplayString
    MAX-ACCESS  read-only
    STATUS      current
    DESCRIPTION
	"The ouput power factor of master." 
	::= { masterOutputPowerfactor 20}
		
masterOutputPowerfactorTwentyone OBJECT-TYPE
    SYNTAX      DisplayString
    MAX-ACCESS  read-only
    STATUS      current
    DESCRIPTION
	"The ouput power factor of master." 
	::= { masterOutputPowerfactor 21}
		
masterOutputPowerfactorTwentytwo OBJECT-TYPE
    SYNTAX      DisplayString
    MAX-ACCESS  read-only
    STATUS      current
    DESCRIPTION
	"The ouput power factor of master." 
	::= { masterOutputPowerfactor 22}
		
masterOutputPowerfactorTwentythree OBJECT-TYPE
    SYNTAX      DisplayString
    MAX-ACCESS  read-only
    STATUS      current
    DESCRIPTION
	"The ouput power factor of master." 
	::= { masterOutputPowerfactor 23}
		
masterOutputPowerfactorTwentyfour OBJECT-TYPE
    SYNTAX      DisplayString
    MAX-ACCESS  read-only
    STATUS      current
    DESCRIPTION
	"The ouput power factor of master." 
	::= { masterOutputPowerfactor 24}
		
masterOutputPowerfactorTwentyfive OBJECT-TYPE
    SYNTAX      DisplayString
    MAX-ACCESS  read-only
    STATUS      current
    DESCRIPTION
	"The ouput power factor of master." 
	::= { masterOutputPowerfactor 25}
		
masterOutputPowerfactorTwentysix OBJECT-TYPE
    SYNTAX      DisplayString
    MAX-ACCESS  read-only
    STATUS      current
    DESCRIPTION
	"The ouput power factor of master." 
	::= { masterOutputPowerfactor 26}
		
masterOutputPowerfactorTwentyseven OBJECT-TYPE
    SYNTAX      DisplayString
    MAX-ACCESS  read-only
    STATUS      current
    DESCRIPTION
	"The ouput power factor of master." 
	::= { masterOutputPowerfactor 27}
		
masterOutputPowerfactorTwentyeight OBJECT-TYPE
    SYNTAX      DisplayString
    MAX-ACCESS  read-only
    STATUS      current
    DESCRIPTION
	"The ouput power factor of master." 
	::= { masterOutputPowerfactor 28}
		
masterOutputPowerfactorTwentynine OBJECT-TYPE
    SYNTAX      DisplayString
    MAX-ACCESS  read-only
    STATUS      current
    DESCRIPTION
	"The ouput power factor of master." 
	::= { masterOutputPowerfactor 29}
		
masterOutputPowerfactorThirty OBJECT-TYPE
    SYNTAX      DisplayString
    MAX-ACCESS  read-only
    STATUS      current
    DESCRIPTION
	"The ouput power factor of master." 
	::= { masterOutputPowerfactor 30}
		
masterOutputPowerfactorThirtyone OBJECT-TYPE
    SYNTAX      DisplayString
    MAX-ACCESS  read-only
    STATUS      current
    DESCRIPTION
	"The ouput power factor of master." 
	::= { masterOutputPowerfactor 31}
		
masterOutputPowerfactorThirtytwo OBJECT-TYPE
    SYNTAX      DisplayString
    MAX-ACCESS  read-only
    STATUS      current
    DESCRIPTION
	"The ouput power factor of master." 
	::= { masterOutputPowerfactor 32}
		
masterOutputPowerfactorThirtythree OBJECT-TYPE
    SYNTAX      DisplayString
    MAX-ACCESS  read-only
    STATUS      current
    DESCRIPTION
	"The ouput power factor of master." 
	::= { masterOutputPowerfactor 33}	
	
masterOutputPowerfactorThirtyfour OBJECT-TYPE
    SYNTAX      DisplayString
    MAX-ACCESS  read-only
    STATUS      current
    DESCRIPTION
	"The ouput power factor of master." 
	::= { masterOutputPowerfactor 34}
	
	
masterOutputPowerfactorThirtyfive OBJECT-TYPE
    SYNTAX      DisplayString
    MAX-ACCESS  read-only
    STATUS      current
    DESCRIPTION
	"The ouput power factor of master." 
	::= { masterOutputPowerfactor 35}
		
masterOutputPowerfactorThirtysix OBJECT-TYPE
    SYNTAX      DisplayString
    MAX-ACCESS  read-only
    STATUS      current
    DESCRIPTION
	"The ouput power factor of master." 
	::= { masterOutputPowerfactor 36}
		
masterOutputPowerfactorThirtyseven OBJECT-TYPE
    SYNTAX      DisplayString
    MAX-ACCESS  read-only
    STATUS      current
    DESCRIPTION
	"The ouput power factor of master." 
	::= { masterOutputPowerfactor 37}
		
masterOutputPowerfactorThirtyeight OBJECT-TYPE
    SYNTAX      DisplayString
    MAX-ACCESS  read-only
    STATUS      current
    DESCRIPTION
	"The ouput power factor of master." 
	::= { masterOutputPowerfactor 38}
		
masterOutputPowerfactorThirtynine OBJECT-TYPE
    SYNTAX      DisplayString
    MAX-ACCESS  read-only
    STATUS      current
    DESCRIPTION
	"The ouput power factor of master." 
	::= { masterOutputPowerfactor 39}
		
masterOutputPowerfactorFourty OBJECT-TYPE
    SYNTAX      DisplayString
    MAX-ACCESS  read-only
    STATUS      current
    DESCRIPTION
	"The ouput power factor of master." 
	::= { masterOutputPowerfactor 40}
		
masterOutputPowerfactorFourtyone OBJECT-TYPE
    SYNTAX      DisplayString
    MAX-ACCESS  read-only
    STATUS      current
    DESCRIPTION
	"The ouput power factor of master." 
	::= { masterOutputPowerfactor 41}
		
masterOutputPowerfactorFourtytwo OBJECT-TYPE
    SYNTAX      DisplayString
    MAX-ACCESS  read-only
    STATUS      current
    DESCRIPTION
	"The ouput power factor of master." 
	::= { masterOutputPowerfactor 42}	
	
-------------------------------master output energy------------------------	
masterOutputEnergy OBJECT IDENTIFIER ::= { master 10}

masterOutputEnergyOne OBJECT-TYPE
    SYNTAX      DisplayString
    MAX-ACCESS  read-only
    STATUS      current
    DESCRIPTION
	"The ouput power of master." 
	::= { masterOutputEnergy 1}

masterOutputEnergyTwo OBJECT-TYPE
    SYNTAX      DisplayString
    MAX-ACCESS  read-only
    STATUS      current
    DESCRIPTION
	"The ouput power of master." 
	::= { masterOutputEnergy 2}
	
masterOutputEnergyThree OBJECT-TYPE
    SYNTAX      DisplayString
    MAX-ACCESS  read-only
    STATUS      current
    DESCRIPTION
	"The ouput power of master." 
	::= { masterOutputEnergy 3}
	
masterOutputEnergyFour OBJECT-TYPE
    SYNTAX      DisplayString
    MAX-ACCESS  read-only
    STATUS      current
    DESCRIPTION
	"The ouput power of master." 
	::= { masterOutputEnergy 4}
		
masterOutputEnergyFive OBJECT-TYPE
    SYNTAX      DisplayString
    MAX-ACCESS  read-only
    STATUS      current
    DESCRIPTION
	"The ouput power of master." 
	::= { masterOutputEnergy 5}
	
masterOutputEnergySix OBJECT-TYPE
    SYNTAX      DisplayString
    MAX-ACCESS  read-only
    STATUS      current
    DESCRIPTION
	"The ouput power of master." 
	::= { masterOutputEnergy 6}
	
masterOutputEnergySeven OBJECT-TYPE
    SYNTAX      DisplayString
    MAX-ACCESS  read-only
    STATUS      current
    DESCRIPTION
	"The ouput power of master." 
	::= { masterOutputEnergy 7}	
	
masterOutputEnergyEight OBJECT-TYPE
    SYNTAX      DisplayString
    MAX-ACCESS  read-only
    STATUS      current
    DESCRIPTION
	"The ouput power of master." 
	::= { masterOutputEnergy 8}
	
masterOutputEnergyNine OBJECT-TYPE
    SYNTAX      DisplayString
    MAX-ACCESS  read-only
    STATUS      current
    DESCRIPTION
	"The ouput power of master." 
	::= { masterOutputEnergy 9}
		
masterOutputEnergyTen OBJECT-TYPE
    SYNTAX      DisplayString
    MAX-ACCESS  read-only
    STATUS      current
    DESCRIPTION
	"The ouput power of master." 
	::= { masterOutputEnergy 10}
		
masterOutputEnergyEleven OBJECT-TYPE
    SYNTAX      DisplayString
    MAX-ACCESS  read-only
    STATUS      current
    DESCRIPTION
	"The ouput power of master." 
	::= { masterOutputEnergy 11}
		
masterOutputEnergyTwel OBJECT-TYPE
    SYNTAX      DisplayString
    MAX-ACCESS  read-only
    STATUS      current
    DESCRIPTION
	"The ouput power of master." 
	::= { masterOutputEnergy 12}
		
masterOutputEnergyThirteen OBJECT-TYPE
    SYNTAX      DisplayString
    MAX-ACCESS  read-only
    STATUS      current
    DESCRIPTION
	"The ouput power of master." 
	::= { masterOutputEnergy 13}
		
masterOutputEnergyFourteen OBJECT-TYPE
    SYNTAX      DisplayString
    MAX-ACCESS  read-only
    STATUS      current
    DESCRIPTION
	"The ouput power of master." 
	::= { masterOutputEnergy 14}
		
masterOutputEnergyFifteen OBJECT-TYPE
    SYNTAX      DisplayString
    MAX-ACCESS  read-only
    STATUS      current
    DESCRIPTION
	"The ouput power of master." 
	::= { masterOutputEnergy 15}
		
masterOutputEnergySixteen OBJECT-TYPE
    SYNTAX      DisplayString
    MAX-ACCESS  read-only
    STATUS      current
    DESCRIPTION
	"The ouput power of master." 
	::= { masterOutputEnergy 16}
		
masterOutputEnergySeventeen OBJECT-TYPE
    SYNTAX      DisplayString
    MAX-ACCESS  read-only
    STATUS      current
    DESCRIPTION
	"The ouput power of master." 
	::= { masterOutputEnergy 17}
		
masterOutputEnergyEighteen OBJECT-TYPE
    SYNTAX      DisplayString
    MAX-ACCESS  read-only
    STATUS      current
    DESCRIPTION
	"The ouput power of master." 
	::= { masterOutputEnergy 18}
		
masterOutputEnergyNineteen OBJECT-TYPE
    SYNTAX      DisplayString
    MAX-ACCESS  read-only
    STATUS      current
    DESCRIPTION
	"The ouput power of master." 
	::= { masterOutputEnergy 19}
		
masterOutputEnergyTwenty OBJECT-TYPE
    SYNTAX      DisplayString
    MAX-ACCESS  read-only
    STATUS      current
    DESCRIPTION
	"The ouput power of master." 
	::= { masterOutputEnergy 20}
		
masterOutputEnergyTwentyone OBJECT-TYPE
    SYNTAX      DisplayString
    MAX-ACCESS  read-only
    STATUS      current
    DESCRIPTION
	"The ouput power of master." 
	::= { masterOutputEnergy 21}
		
masterOutputEnergyTwentytwo OBJECT-TYPE
    SYNTAX      DisplayString
    MAX-ACCESS  read-only
    STATUS      current
    DESCRIPTION
	"The ouput power of master." 
	::= { masterOutputEnergy 22}
		
masterOutputEnergyTwentythree OBJECT-TYPE
    SYNTAX      DisplayString
    MAX-ACCESS  read-only
    STATUS      current
    DESCRIPTION
	"The ouput power of master." 
	::= { masterOutputEnergy 23}
		
masterOutputEnergyTwentyfour OBJECT-TYPE
    SYNTAX      DisplayString
    MAX-ACCESS  read-only
    STATUS      current
    DESCRIPTION
	"The ouput power of master." 
	::= { masterOutputEnergy 24}
		
masterOutputEnergyTwentyfive OBJECT-TYPE
    SYNTAX      DisplayString
    MAX-ACCESS  read-only
    STATUS      current
    DESCRIPTION
	"The ouput power of master." 
	::= { masterOutputEnergy 25}
		
masterOutputEnergyTwentysix OBJECT-TYPE
    SYNTAX      DisplayString
    MAX-ACCESS  read-only
    STATUS      current
    DESCRIPTION
	"The ouput power of master." 
	::= { masterOutputEnergy 26}
		
masterOutputEnergyTwentyseven OBJECT-TYPE
    SYNTAX      DisplayString
    MAX-ACCESS  read-only
    STATUS      current
    DESCRIPTION
	"The ouput power of master." 
	::= { masterOutputEnergy 27}
		
masterOutputEnergyTwentyeight OBJECT-TYPE
    SYNTAX      DisplayString
    MAX-ACCESS  read-only
    STATUS      current
    DESCRIPTION
	"The ouput power of master." 
	::= { masterOutputEnergy 28}
		
masterOutputEnergyTwentynine OBJECT-TYPE
    SYNTAX      DisplayString
    MAX-ACCESS  read-only
    STATUS      current
    DESCRIPTION
	"The ouput power of master." 
	::= { masterOutputEnergy 29}
		
masterOutputEnergyThirty OBJECT-TYPE
    SYNTAX      DisplayString
    MAX-ACCESS  read-only
    STATUS      current
    DESCRIPTION
	"The ouput power of master." 
	::= { masterOutputEnergy 30}
		
masterOutputEnergyThirtyone OBJECT-TYPE
    SYNTAX      DisplayString
    MAX-ACCESS  read-only
    STATUS      current
    DESCRIPTION
	"The ouput power of master." 
	::= { masterOutputEnergy 31}
		
masterOutputEnergyThirtytwo OBJECT-TYPE
    SYNTAX      DisplayString
    MAX-ACCESS  read-only
    STATUS      current
    DESCRIPTION
	"The ouput power of master." 
	::= { masterOutputEnergy 32}
		
masterOutputEnergyThirtythree OBJECT-TYPE
    SYNTAX      DisplayString
    MAX-ACCESS  read-only
    STATUS      current
    DESCRIPTION
	"The ouput power of master." 
	::= { masterOutputEnergy 33}	
	
masterOutputEnergyThirtyfour OBJECT-TYPE
    SYNTAX      DisplayString
    MAX-ACCESS  read-only
    STATUS      current
    DESCRIPTION
	"The ouput power of master." 
	::= { masterOutputEnergy 34}
	
	
masterOutputEnergyThirtyfive OBJECT-TYPE
    SYNTAX      DisplayString
    MAX-ACCESS  read-only
    STATUS      current
    DESCRIPTION
	"The ouput power of master." 
	::= { masterOutputEnergy 35}
		
masterOutputEnergyThirtysix OBJECT-TYPE
    SYNTAX      DisplayString
    MAX-ACCESS  read-only
    STATUS      current
    DESCRIPTION
	"The ouput power of master." 
	::= { masterOutputEnergy 36}
		
masterOutputEnergyThirtyseven OBJECT-TYPE
    SYNTAX      DisplayString
    MAX-ACCESS  read-only
    STATUS      current
    DESCRIPTION
	"The ouput power of master." 
	::= { masterOutputEnergy 37}
		
masterOutputEnergyThirtyeight OBJECT-TYPE
    SYNTAX      DisplayString
    MAX-ACCESS  read-only
    STATUS      current
    DESCRIPTION
	"The ouput power of master." 
	::= { masterOutputEnergy 38}
		
masterOutputEnergyThirtynine OBJECT-TYPE
    SYNTAX      DisplayString
    MAX-ACCESS  read-only
    STATUS      current
    DESCRIPTION
	"The ouput power of master." 
	::= { masterOutputEnergy 39}
		
masterOutputEnergyFourty OBJECT-TYPE
    SYNTAX      DisplayString
    MAX-ACCESS  read-only
    STATUS      current
    DESCRIPTION
	"The ouput power of master." 
	::= { masterOutputEnergy 40}
		
masterOutputEnergyFourtyone OBJECT-TYPE
    SYNTAX      DisplayString
    MAX-ACCESS  read-only
    STATUS      current
    DESCRIPTION
	"The ouput power of master." 
	::= { masterOutputEnergy 41}
		
masterOutputEnergyFourtytwo OBJECT-TYPE
    SYNTAX      DisplayString
    MAX-ACCESS  read-only
    STATUS      current
    DESCRIPTION
	"The ouput power of master." 
	::= { masterOutputEnergy 42}		




-------------------------------slave1 information--------------------
slave1 OBJECT IDENTIFIER ::= { pdu 2}
slave1Information OBJECT IDENTIFIER ::= { slave1 1}
slave1Name OBJECT-TYPE
    SYNTAX      DisplayString
    MAX-ACCESS  read-write
    STATUS      current
    DESCRIPTION
	"This is the first device."
    ::= { slave1Information 1}
    
slave1Type OBJECT-TYPE
    SYNTAX      DisplayString
    MAX-ACCESS  read-only
    STATUS      current
    DESCRIPTION
	"This is device type "
    ::= { slave1Information 2}
    
slave1OutputNumber OBJECT-TYPE 
    SYNTAX      Integer32
    MAX-ACCESS  read-only
    STATUS      current
    DESCRIPTION
	"This is the number of output bits"
	::= { slave1Information 3}
	
slave1MacAdress OBJECT-TYPE
    SYNTAX      DisplayString
    MAX-ACCESS  read-only
    STATUS      current
    DESCRIPTION
	"This is device MAC adress"
    ::= { slave1Information 4}	

slave1Vison OBJECT-TYPE
    SYNTAX      DisplayString
    MAX-ACCESS  read-only
    STATUS      current
    DESCRIPTION
	"This is device vison "
    ::= { slave1Information 5}

slave1Frequency OBJECT-TYPE
    SYNTAX      Integer32
    MAX-ACCESS  read-only
    STATUS      current
    DESCRIPTION
	"This is device frequency "
    ::= { slave1Information 6}
	
slave1Emission OBJECT-TYPE
    SYNTAX      DisplayString
    MAX-ACCESS  read-only
    STATUS      current
    DESCRIPTION
	"This is device emission "
    ::= { slave1Information 7}	
	
slave1RunTime OBJECT-TYPE
    SYNTAX      DisplayString
    MAX-ACCESS  read-only
    STATUS      current
    DESCRIPTION
	"This is device running time "
    ::= { slave1Information 8}	

slave1BuzzerSwitch OBJECT-TYPE
    SYNTAX      DisplayString
    MAX-ACCESS  read-write
    STATUS      current
    DESCRIPTION
	"This is device buzzer switch."
    ::= { slave1Information 9}	

	
-------------------------------slave1 phase--------------------
slave1Phase OBJECT IDENTIFIER ::= { slave1 2}	
	
slave1PhaseOne OBJECT IDENTIFIER ::= { slave1Phase 1}	    
slave1PhaseOneCurrent OBJECT-TYPE
    SYNTAX      DisplayString
    MAX-ACCESS  read-only
    STATUS      current
    DESCRIPTION
	"The power of phase one"
    ::= { slave1PhaseOne 1}

slave1PhaseOneVoltage OBJECT-TYPE
    SYNTAX      DisplayString
    MAX-ACCESS  read-only
    STATUS      current
    DESCRIPTION
	"The power of phase one"
    ::= { slave1PhaseOne 2}

slave1PhaseOnePower OBJECT-TYPE
    SYNTAX      DisplayString
    MAX-ACCESS  read-only
    STATUS      current
    DESCRIPTION
	"The power of phase one"
    ::= { slave1PhaseOne 3}
	
slave1PhaseOnePowerfactor OBJECT-TYPE
    SYNTAX      DisplayString
    MAX-ACCESS  read-only
    STATUS      current
    DESCRIPTION
	"The power of phase one"
    ::= { slave1PhaseOne 4}	
	
slave1PhaseOneEnergy OBJECT-TYPE
    SYNTAX      DisplayString
    MAX-ACCESS  read-only
    STATUS      current
    DESCRIPTION
	"The power of phase one"
    ::= { slave1PhaseOne 5}	
		
slave1PhaseOneCurrentMin OBJECT-TYPE
    SYNTAX      DisplayString
    MAX-ACCESS  read-write
    STATUS      current
    DESCRIPTION
	"The power of phase one"
    ::= { slave1PhaseOne 6}	
	
slave1PhaseOneCurrentMinCritical OBJECT-TYPE
    SYNTAX      DisplayString
    MAX-ACCESS  read-write
    STATUS      current
    DESCRIPTION
	"The power of phase one"
    ::= { slave1PhaseOne 7}
	
slave1PhaseOneCurrentMaxCritical OBJECT-TYPE
    SYNTAX      DisplayString
    MAX-ACCESS  read-write
    STATUS      current
    DESCRIPTION
	"The power of phase one"
    ::= { slave1PhaseOne 8}
	
slave1PhaseOneCurrentMax OBJECT-TYPE
    SYNTAX      DisplayString
    MAX-ACCESS  read-write
    STATUS      current
    DESCRIPTION
	"The power of phase one"
    ::= { slave1PhaseOne 9}
	
slave1PhaseOneVoltageMin OBJECT-TYPE
    SYNTAX      DisplayString
    MAX-ACCESS  read-write
    STATUS      current
    DESCRIPTION
	"The power of phase one"
    ::= { slave1PhaseOne 10}
	
slave1PhaseOneVoltageMinCritical OBJECT-TYPE
    SYNTAX      DisplayString
    MAX-ACCESS  read-write
    STATUS      current
    DESCRIPTION
	"The power of phase one"
    ::= { slave1PhaseOne 11}

slave1PhaseOneVoltageMaxCritical OBJECT-TYPE
    SYNTAX      DisplayString
    MAX-ACCESS  read-write
    STATUS      current
    DESCRIPTION
	"The power of phase one"
    ::= { slave1PhaseOne 12}
	
slave1PhaseOneVoltageMax OBJECT-TYPE
    SYNTAX      DisplayString
    MAX-ACCESS  read-write
    STATUS      current
    DESCRIPTION
	"The power of phase one"
    ::= { slave1PhaseOne 13}


slave1PhaseTwo OBJECT IDENTIFIER ::= { slave1Phase 2}	    
slave1PhaseTwoCurrent OBJECT-TYPE
    SYNTAX      DisplayString
    MAX-ACCESS  read-only
    STATUS      current
    DESCRIPTION
	"The power of phase one"
    ::= { slave1PhaseTwo 1}

slave1PhaseTwoVoltage OBJECT-TYPE
    SYNTAX      DisplayString
    MAX-ACCESS  read-only
    STATUS      current
    DESCRIPTION
	"The power of phase one"
    ::= { slave1PhaseTwo 2}

slave1PhaseTwoPower OBJECT-TYPE
    SYNTAX      DisplayString
    MAX-ACCESS  read-only
    STATUS      current
    DESCRIPTION
	"The power of phase one"
    ::= { slave1PhaseTwo 3}
	
slave1PhaseTwoPowerfactor OBJECT-TYPE
    SYNTAX      DisplayString
    MAX-ACCESS  read-only
    STATUS      current
    DESCRIPTION
	"The power of phase one"
    ::= { slave1PhaseTwo 4}	
	
slave1PhaseTwoEnergy OBJECT-TYPE
    SYNTAX      DisplayString
    MAX-ACCESS  read-only
    STATUS      current
    DESCRIPTION
	"The power of phase one"
    ::= { slave1PhaseTwo 5}	
		
slave1PhaseTwoCurrentMin OBJECT-TYPE
    SYNTAX      DisplayString
    MAX-ACCESS  read-write
    STATUS      current
    DESCRIPTION
	"The power of phase one"
    ::= { slave1PhaseTwo 6}	
	
slave1PhaseTwoCurrentMinCritical OBJECT-TYPE
    SYNTAX      DisplayString
    MAX-ACCESS  read-write
    STATUS      current
    DESCRIPTION
	"The power of phase one"
    ::= { slave1PhaseTwo 7}
	
slave1PhaseTwoCurrentMaxCritical OBJECT-TYPE
    SYNTAX      DisplayString
    MAX-ACCESS  read-write
    STATUS      current
    DESCRIPTION
	"The power of phase one"
    ::= { slave1PhaseTwo 8}
	
slave1PhaseTwoCurrentMax OBJECT-TYPE
    SYNTAX      DisplayString
    MAX-ACCESS  read-write
    STATUS      current
    DESCRIPTION
	"The power of phase one"
    ::= { slave1PhaseTwo 9}
	
slave1PhaseTwoVoltageMin OBJECT-TYPE
    SYNTAX      DisplayString
    MAX-ACCESS  read-write
    STATUS      current
    DESCRIPTION
	"The power of phase one"
    ::= { slave1PhaseTwo 10}
	
slave1PhaseTwoVoltageMinCritical OBJECT-TYPE
    SYNTAX      DisplayString
    MAX-ACCESS  read-write
    STATUS      current
    DESCRIPTION
	"The power of phase one"
    ::= { slave1PhaseTwo 11}

slave1PhaseTwoVoltageMaxCritical OBJECT-TYPE
    SYNTAX      DisplayString
    MAX-ACCESS  read-write
    STATUS      current
    DESCRIPTION
	"The power of phase one"
    ::= { slave1PhaseTwo 12}
	
slave1PhaseTwoVoltageMax OBJECT-TYPE
    SYNTAX      DisplayString
    MAX-ACCESS  read-write
    STATUS      current
    DESCRIPTION
	"The power of phase one"
    ::= { slave1PhaseTwo 13}
	
	
slave1PhaseThree OBJECT IDENTIFIER ::= { slave1Phase 3}	    
slave1PhaseThreeCurrent OBJECT-TYPE
    SYNTAX      DisplayString
    MAX-ACCESS  read-only
    STATUS      current
    DESCRIPTION
	"The power of phase one"
    ::= { slave1PhaseThree 1}

slave1PhaseThreeVoltage OBJECT-TYPE
    SYNTAX      DisplayString
    MAX-ACCESS  read-only
    STATUS      current
    DESCRIPTION
	"The power of phase one"
    ::= { slave1PhaseThree 2}

slave1PhaseThreePower OBJECT-TYPE
    SYNTAX      DisplayString
    MAX-ACCESS  read-only
    STATUS      current
    DESCRIPTION
	"The power of phase one"
    ::= { slave1PhaseThree 3}
	
slave1PhaseThreePowerfactor OBJECT-TYPE
    SYNTAX      DisplayString
    MAX-ACCESS  read-only
    STATUS      current
    DESCRIPTION
	"The power of phase one"
    ::= { slave1PhaseThree 4}	
	
slave1PhaseThreeEnergy OBJECT-TYPE
    SYNTAX      DisplayString
    MAX-ACCESS  read-only
    STATUS      current
    DESCRIPTION
	"The power of phase one"
    ::= { slave1PhaseThree 5}	
		
slave1PhaseThreeCurrentMin OBJECT-TYPE
    SYNTAX      DisplayString
    MAX-ACCESS  read-write
    STATUS      current
    DESCRIPTION
	"The power of phase one"
    ::= { slave1PhaseThree 6}	
	
slave1PhaseThreeCurrentMinCritical OBJECT-TYPE
    SYNTAX      DisplayString
    MAX-ACCESS  read-write
    STATUS      current
    DESCRIPTION
	"The power of phase one"
    ::= { slave1PhaseThree 7}
	
slave1PhaseThreeCurrentMaxCritical OBJECT-TYPE
    SYNTAX      DisplayString
    MAX-ACCESS  read-write
    STATUS      current
    DESCRIPTION
	"The power of phase one"
    ::= { slave1PhaseThree 8}
	
slave1PhaseThreeCurrentMax OBJECT-TYPE
    SYNTAX      DisplayString
    MAX-ACCESS  read-write
    STATUS      current
    DESCRIPTION
	"The power of phase one"
    ::= { slave1PhaseThree 9}
	
slave1PhaseThreeVoltageMin OBJECT-TYPE
    SYNTAX      DisplayString
    MAX-ACCESS  read-write
    STATUS      current
    DESCRIPTION
	"The power of phase one"
    ::= { slave1PhaseThree 10}
	
slave1PhaseThreeVoltageMinCritical OBJECT-TYPE
    SYNTAX      DisplayString
    MAX-ACCESS  read-write
    STATUS      current
    DESCRIPTION
	"The power of phase one"
    ::= { slave1PhaseThree 11}

slave1PhaseThreeVoltageMaxCritical OBJECT-TYPE
    SYNTAX      DisplayString
    MAX-ACCESS  read-write
    STATUS      current
    DESCRIPTION
	"The power of phase one"
    ::= { slave1PhaseThree 12}
	
slave1PhaseThreeVoltageMax OBJECT-TYPE
    SYNTAX      DisplayString
    MAX-ACCESS  read-write
    STATUS      current
    DESCRIPTION
	"The power of phase one"
    ::= { slave1PhaseThree 13}
	
	
-------------------------------slave1 circuit--------------------	
slave1Circuit OBJECT IDENTIFIER ::= { slave1 3}	

slave1CircuitOne OBJECT IDENTIFIER ::= { slave1Circuit 1}	    
slave1CircuitOneBreaker OBJECT-TYPE
    SYNTAX      DisplayString
    MAX-ACCESS  read-only
    STATUS      current
    DESCRIPTION
	"The power of phase one"
    ::= { slave1CircuitOne 1}
	
slave1CircuitOneManagementBit OBJECT-TYPE
    SYNTAX      DisplayString
    MAX-ACCESS  read-only
    STATUS      current
    DESCRIPTION
	"The power of phase one"
    ::= { slave1CircuitOne 2}	

slave1CircuitOneCurrent OBJECT-TYPE
    SYNTAX      DisplayString
    MAX-ACCESS  read-only
    STATUS      current
    DESCRIPTION
	"The power of phase one"
    ::= { slave1CircuitOne 3}

slave1CircuitOneVoltage OBJECT-TYPE
    SYNTAX      DisplayString
    MAX-ACCESS  read-only
    STATUS      current
    DESCRIPTION
	"The power of phase one"
    ::= { slave1CircuitOne 4}

slave1CircuitOneEnergy OBJECT-TYPE
    SYNTAX      DisplayString
    MAX-ACCESS  read-only
    STATUS      current
    DESCRIPTION
	"The power of phase one"
    ::= { slave1CircuitOne 5}	
	
slave1CircuitOnePower OBJECT-TYPE
    SYNTAX      DisplayString
    MAX-ACCESS  read-only
    STATUS      current
    DESCRIPTION
	"The power of phase one"
    ::= { slave1CircuitOne 6}
	
slave1CircuitOneCurrentMin OBJECT-TYPE
    SYNTAX      DisplayString
    MAX-ACCESS  read-write
    STATUS      current
    DESCRIPTION
	"The power of phase one"
    ::= { slave1CircuitOne 7}	
	
slave1CircuitOneCurrentMinCritical OBJECT-TYPE
    SYNTAX      DisplayString
    MAX-ACCESS  read-write
    STATUS      current
    DESCRIPTION
	"The power of phase one"
    ::= { slave1CircuitOne 8}
	
slave1CircuitOneCurrentMaxCritical OBJECT-TYPE
    SYNTAX      DisplayString
    MAX-ACCESS  read-write
    STATUS      current
    DESCRIPTION
	"The power of phase one"
    ::= { slave1CircuitOne 9}
	
slave1CircuitOneCurrentMax OBJECT-TYPE
    SYNTAX      DisplayString
    MAX-ACCESS  read-write
    STATUS      current
    DESCRIPTION
	"The power of phase one"
    ::= { slave1CircuitOne 10}
	

slave1CircuitTwo OBJECT IDENTIFIER ::= { slave1Circuit 2}	    
slave1CircuitTwoBreaker OBJECT-TYPE
    SYNTAX      DisplayString
    MAX-ACCESS  read-only
    STATUS      current
    DESCRIPTION
	"The power of phase one"
    ::= { slave1CircuitTwo 1}
	
slave1CircuitTwoManagementBit OBJECT-TYPE
    SYNTAX      DisplayString
    MAX-ACCESS  read-only
    STATUS      current
    DESCRIPTION
	"The power of phase one"
    ::= { slave1CircuitTwo 2}	

slave1CircuitTwoCurrent OBJECT-TYPE
    SYNTAX      DisplayString
    MAX-ACCESS  read-only
    STATUS      current
    DESCRIPTION
	"The power of phase one"
    ::= { slave1CircuitTwo 3}

slave1CircuitTwoVoltage OBJECT-TYPE
    SYNTAX      DisplayString
    MAX-ACCESS  read-only
    STATUS      current
    DESCRIPTION
	"The power of phase one"
    ::= { slave1CircuitTwo 4}

slave1CircuitTwoEnergy OBJECT-TYPE
    SYNTAX      DisplayString
    MAX-ACCESS  read-only
    STATUS      current
    DESCRIPTION
	"The power of phase one"
    ::= { slave1CircuitTwo 5}	
	
slave1CircuitTwoPower OBJECT-TYPE
    SYNTAX      DisplayString
    MAX-ACCESS  read-only
    STATUS      current
    DESCRIPTION
	"The power of phase one"
    ::= { slave1CircuitTwo 6}
	
slave1CircuitTwoCurrentMin OBJECT-TYPE
    SYNTAX      DisplayString
    MAX-ACCESS  read-write
    STATUS      current
    DESCRIPTION
	"The power of phase one"
    ::= { slave1CircuitTwo 7}	
	
slave1CircuitTwoCurrentMinCritical OBJECT-TYPE
    SYNTAX      DisplayString
    MAX-ACCESS  read-write
    STATUS      current
    DESCRIPTION
	"The power of phase one"
    ::= { slave1CircuitTwo 8}
	
slave1CircuitTwoCurrentMaxCritical OBJECT-TYPE
    SYNTAX      DisplayString
    MAX-ACCESS  read-write
    STATUS      current
    DESCRIPTION
	"The power of phase one"
    ::= { slave1CircuitTwo 9}
	
slave1CircuitTwoCurrentMax OBJECT-TYPE
    SYNTAX      DisplayString
    MAX-ACCESS  read-write
    STATUS      current
    DESCRIPTION
	"The power of phase one"
    ::= { slave1CircuitTwo 10}
	
	
slave1CircuitThree OBJECT IDENTIFIER ::= { slave1Circuit 3}	    
slave1CircuitThreeBreaker OBJECT-TYPE
    SYNTAX      DisplayString
    MAX-ACCESS  read-only
    STATUS      current
    DESCRIPTION
	"The power of phase one"
    ::= { slave1CircuitThree 1}
	
slave1CircuitThreeManagementBit OBJECT-TYPE
    SYNTAX      DisplayString
    MAX-ACCESS  read-only
    STATUS      current
    DESCRIPTION
	"The power of phase one"
    ::= { slave1CircuitThree 2}	

slave1CircuitThreeCurrent OBJECT-TYPE
    SYNTAX      DisplayString
    MAX-ACCESS  read-only
    STATUS      current
    DESCRIPTION
	"The power of phase one"
    ::= { slave1CircuitThree 3}

slave1CircuitThreeVoltage OBJECT-TYPE
    SYNTAX      DisplayString
    MAX-ACCESS  read-only
    STATUS      current
    DESCRIPTION
	"The power of phase one"
    ::= { slave1CircuitThree 4}

slave1CircuitThreeEnergy OBJECT-TYPE
    SYNTAX      DisplayString
    MAX-ACCESS  read-only
    STATUS      current
    DESCRIPTION
	"The power of phase one"
    ::= { slave1CircuitThree 5}	
	
slave1CircuitThreePower OBJECT-TYPE
    SYNTAX      DisplayString
    MAX-ACCESS  read-only
    STATUS      current
    DESCRIPTION
	"The power of phase one"
    ::= { slave1CircuitThree 6}
	
slave1CircuitThreeCurrentMin OBJECT-TYPE
    SYNTAX      DisplayString
    MAX-ACCESS  read-write
    STATUS      current
    DESCRIPTION
	"The power of phase one"
    ::= { slave1CircuitThree 7}	
	
slave1CircuitThreeCurrentMinCritical OBJECT-TYPE
    SYNTAX      DisplayString
    MAX-ACCESS  read-write
    STATUS      current
    DESCRIPTION
	"The power of phase one"
    ::= { slave1CircuitThree 8}
	
slave1CircuitThreeCurrentMaxCritical OBJECT-TYPE
    SYNTAX      DisplayString
    MAX-ACCESS  read-write
    STATUS      current
    DESCRIPTION
	"The power of phase one"
    ::= { slave1CircuitThree 9}
	
slave1CircuitThreeCurrentMax OBJECT-TYPE
    SYNTAX      DisplayString
    MAX-ACCESS  read-write
    STATUS      current
    DESCRIPTION
	"The power of phase one"
    ::= { slave1CircuitThree 10}
	
	
slave1CircuitFour OBJECT IDENTIFIER ::= { slave1Circuit 4}	    
slave1CircuitFourBreaker OBJECT-TYPE
    SYNTAX      DisplayString
    MAX-ACCESS  read-only
    STATUS      current
    DESCRIPTION
	"The power of phase one"
    ::= { slave1CircuitFour 1}
	
slave1CircuitFourManagementBit OBJECT-TYPE
    SYNTAX      DisplayString
    MAX-ACCESS  read-only
    STATUS      current
    DESCRIPTION
	"The power of phase one"
    ::= { slave1CircuitFour 2}	

slave1CircuitFourCurrent OBJECT-TYPE
    SYNTAX      DisplayString
    MAX-ACCESS  read-only
    STATUS      current
    DESCRIPTION
	"The power of phase one"
    ::= { slave1CircuitFour 3}

slave1CircuitFourVoltage OBJECT-TYPE
    SYNTAX      DisplayString
    MAX-ACCESS  read-only
    STATUS      current
    DESCRIPTION
	"The power of phase one"
    ::= { slave1CircuitFour 4}

slave1CircuitFourEnergy OBJECT-TYPE
    SYNTAX      DisplayString
    MAX-ACCESS  read-only
    STATUS      current
    DESCRIPTION
	"The power of phase one"
    ::= { slave1CircuitFour 5}	
	
slave1CircuitFourPower OBJECT-TYPE
    SYNTAX      DisplayString
    MAX-ACCESS  read-only
    STATUS      current
    DESCRIPTION
	"The power of phase one"
    ::= { slave1CircuitFour 6}
	
slave1CircuitFourCurrentMin OBJECT-TYPE
    SYNTAX      DisplayString
    MAX-ACCESS  read-write
    STATUS      current
    DESCRIPTION
	"The power of phase one"
    ::= { slave1CircuitFour 7}	
	
slave1CircuitFourCurrentMinCritical OBJECT-TYPE
    SYNTAX      DisplayString
    MAX-ACCESS  read-write
    STATUS      current
    DESCRIPTION
	"The power of phase one"
    ::= { slave1CircuitFour 8}
	
slave1CircuitFourCurrentMaxCritical OBJECT-TYPE
    SYNTAX      DisplayString
    MAX-ACCESS  read-write
    STATUS      current
    DESCRIPTION
	"The power of phase one"
    ::= { slave1CircuitFour 9}
	
slave1CircuitFourCurrentMax OBJECT-TYPE
    SYNTAX      DisplayString
    MAX-ACCESS  read-write
    STATUS      current
    DESCRIPTION
	"The power of phase one"
    ::= { slave1CircuitFour 10}
	
	
slave1CircuitFive OBJECT IDENTIFIER ::= { slave1Circuit 5}	    
slave1CircuitFiveBreaker OBJECT-TYPE
    SYNTAX      DisplayString
    MAX-ACCESS  read-only
    STATUS      current
    DESCRIPTION
	"The power of phase one"
    ::= { slave1CircuitFive 1}
	
slave1CircuitFiveManagementBit OBJECT-TYPE
    SYNTAX      DisplayString
    MAX-ACCESS  read-only
    STATUS      current
    DESCRIPTION
	"The power of phase one"
    ::= { slave1CircuitFive 2}	

slave1CircuitFiveCurrent OBJECT-TYPE
    SYNTAX      DisplayString
    MAX-ACCESS  read-only
    STATUS      current
    DESCRIPTION
	"The power of phase one"
    ::= { slave1CircuitFive 3}

slave1CircuitFiveVoltage OBJECT-TYPE
    SYNTAX      DisplayString
    MAX-ACCESS  read-only
    STATUS      current
    DESCRIPTION
	"The power of phase one"
    ::= { slave1CircuitFive 4}

slave1CircuitFiveEnergy OBJECT-TYPE
    SYNTAX      DisplayString
    MAX-ACCESS  read-only
    STATUS      current
    DESCRIPTION
	"The power of phase one"
    ::= { slave1CircuitFive 5}	
	
slave1CircuitFivePower OBJECT-TYPE
    SYNTAX      DisplayString
    MAX-ACCESS  read-only
    STATUS      current
    DESCRIPTION
	"The power of phase one"
    ::= { slave1CircuitFive 6}
		
slave1CircuitFiveCurrentMin OBJECT-TYPE
    SYNTAX      DisplayString
    MAX-ACCESS  read-write
    STATUS      current
    DESCRIPTION
	"The power of phase one"
    ::= { slave1CircuitFive 7}	
	
slave1CircuitFiveCurrentMinCritical OBJECT-TYPE
    SYNTAX      DisplayString
    MAX-ACCESS  read-write
    STATUS      current
    DESCRIPTION
	"The power of phase one"
    ::= { slave1CircuitFive 8}
	
slave1CircuitFiveCurrentMaxCritical OBJECT-TYPE
    SYNTAX      DisplayString
    MAX-ACCESS  read-write
    STATUS      current
    DESCRIPTION
	"The power of phase one"
    ::= { slave1CircuitFive 9}
	
slave1CircuitFiveCurrentMax OBJECT-TYPE
    SYNTAX      DisplayString
    MAX-ACCESS  read-write
    STATUS      current
    DESCRIPTION
	"The power of phase one"
    ::= { slave1CircuitFive 10}

	
slave1CircuitSix OBJECT IDENTIFIER ::= { slave1Circuit 6}	    
slave1CircuitSixBreaker OBJECT-TYPE
    SYNTAX      DisplayString
    MAX-ACCESS  read-only
    STATUS      current
    DESCRIPTION
	"The power of phase one"
    ::= { slave1CircuitSix 1}
	
slave1CircuitSixManagementBit OBJECT-TYPE
    SYNTAX      DisplayString
    MAX-ACCESS  read-only
    STATUS      current
    DESCRIPTION
	"The power of phase one"
    ::= { slave1CircuitSix 2}	

slave1CircuitSixCurrent OBJECT-TYPE
    SYNTAX      DisplayString
    MAX-ACCESS  read-only
    STATUS      current
    DESCRIPTION
	"The power of phase one"
    ::= { slave1CircuitSix 3}

slave1CircuitSixVoltage OBJECT-TYPE
    SYNTAX      DisplayString
    MAX-ACCESS  read-only
    STATUS      current
    DESCRIPTION
	"The power of phase one"
    ::= { slave1CircuitSix 4}

slave1CircuitSixEnergy OBJECT-TYPE
    SYNTAX      DisplayString
    MAX-ACCESS  read-only
    STATUS      current
    DESCRIPTION
	"The power of phase one"
    ::= { slave1CircuitSix 5}	
	
slave1CircuitSixPower OBJECT-TYPE
    SYNTAX      DisplayString
    MAX-ACCESS  read-only
    STATUS      current
    DESCRIPTION
	"The power of phase one"
    ::= { slave1CircuitSix 6}
	
slave1CircuitSixCurrentMin OBJECT-TYPE
    SYNTAX      DisplayString
    MAX-ACCESS  read-write
    STATUS      current
    DESCRIPTION
	"The power of phase one"
    ::= { slave1CircuitSix 7}	
	
slave1CircuitSixCurrentMinCritical OBJECT-TYPE
    SYNTAX      DisplayString
    MAX-ACCESS  read-write
    STATUS      current
    DESCRIPTION
	"The power of phase one"
    ::= { slave1CircuitSix 8}
	
slave1CircuitSixCurrentMaxCritical OBJECT-TYPE
    SYNTAX      DisplayString
    MAX-ACCESS  read-write
    STATUS      current
    DESCRIPTION
	"The power of phase one"
    ::= { slave1CircuitSix 9}
	
slave1CircuitSixCurrentMax OBJECT-TYPE
    SYNTAX      DisplayString
    MAX-ACCESS  read-write
    STATUS      current
    DESCRIPTION
	"The power of phase one"
    ::= { slave1CircuitSix 10}

	
-------------------------------slave1 sensor------------------------	
slave1Sensor OBJECT IDENTIFIER ::= { slave1 4}
slave1SensorTemperatureOne OBJECT-TYPE
    SYNTAX      DisplayString
    MAX-ACCESS  read-only
    STATUS      current
    DESCRIPTION
	"This is the first device."
    ::= { slave1Sensor 1}
	
slave1SensorTemperatureTwo OBJECT-TYPE
    SYNTAX      DisplayString
    MAX-ACCESS  read-only
    STATUS      current
    DESCRIPTION
	"This is the first device."
    ::= { slave1Sensor 2}

slave1SensorHumidityOne OBJECT-TYPE
    SYNTAX      DisplayString
    MAX-ACCESS  read-only
    STATUS      current
    DESCRIPTION
	"This is the first device."
    ::= { slave1Sensor 3}

slave1SensorHumidityTwo OBJECT-TYPE
    SYNTAX      DisplayString
    MAX-ACCESS  read-only
    STATUS      current
    DESCRIPTION
	"This is the first device."
    ::= { slave1Sensor 4}	

slave1SensorDoorOne OBJECT-TYPE
    SYNTAX      DisplayString
    MAX-ACCESS  read-only
    STATUS      current
    DESCRIPTION
	"This is the first device."
    ::= { slave1Sensor 5}

slave1SensorDoorTwo OBJECT-TYPE
    SYNTAX      DisplayString
    MAX-ACCESS  read-only
    STATUS      current
    DESCRIPTION
	"This is the first device."
    ::= { slave1Sensor 6}	
	
slave1SensorSmoke OBJECT-TYPE
    SYNTAX      DisplayString
    MAX-ACCESS  read-only
    STATUS      current
    DESCRIPTION
	"This is the first device."
    ::= { slave1Sensor 7}
	
slave1SensorWater OBJECT-TYPE
    SYNTAX      DisplayString
    MAX-ACCESS  read-only
    STATUS      current
    DESCRIPTION
	"This is the first device."
    ::= { slave1Sensor 8}
	
slave1SensorTemperatureOneMin OBJECT-TYPE
    SYNTAX      DisplayString
    MAX-ACCESS  read-write
    STATUS      current
    DESCRIPTION
	"This is the first device."
    ::= { slave1Sensor 9}
	
slave1SensorTemperatureOneMinCritical OBJECT-TYPE
    SYNTAX      DisplayString
    MAX-ACCESS  read-write
    STATUS      current
    DESCRIPTION
	"This is the first device."
    ::= { slave1Sensor 10}	
	
slave1SensorTemperatureOneMaxCritical OBJECT-TYPE
    SYNTAX      DisplayString
    MAX-ACCESS  read-write
    STATUS      current
    DESCRIPTION
	"This is the first device."
    ::= { slave1Sensor 11}
	
slave1SensorTemperatureOneMax OBJECT-TYPE
    SYNTAX      DisplayString
    MAX-ACCESS  read-write
    STATUS      current
    DESCRIPTION
	"This is the first device."
    ::= { slave1Sensor 12}

slave1SensorTemperatureTwoMin OBJECT-TYPE
    SYNTAX      DisplayString
    MAX-ACCESS  read-write
    STATUS      current
    DESCRIPTION
	"This is the first device."
    ::= { slave1Sensor 13}
	
slave1SensorTemperatureTwoMinCritical OBJECT-TYPE
    SYNTAX      DisplayString
    MAX-ACCESS  read-write
    STATUS      current
    DESCRIPTION
	"This is the first device."
    ::= { slave1Sensor 14}	
	
slave1SensorTemperatureTwoMaxCritical OBJECT-TYPE
    SYNTAX      DisplayString
    MAX-ACCESS  read-write
    STATUS      current
    DESCRIPTION
	"This is the first device."
    ::= { slave1Sensor 15}
	
slave1SensorTemperatureTwoMax OBJECT-TYPE
    SYNTAX      DisplayString
    MAX-ACCESS  read-write
    STATUS      current
    DESCRIPTION
	"This is the first device."
    ::= { slave1Sensor 16}
	
slave1SensorHumidityOneMin OBJECT-TYPE
    SYNTAX      DisplayString
    MAX-ACCESS  read-write
    STATUS      current
    DESCRIPTION
	"This is the first device."
    ::= { slave1Sensor 17}
	
slave1SensorHumidityOneMinCritical OBJECT-TYPE
    SYNTAX      DisplayString
    MAX-ACCESS  read-write
    STATUS      current
    DESCRIPTION
	"This is the first device."
    ::= { slave1Sensor 18}	
	
slave1SensorHumidityOneMaxCritical OBJECT-TYPE
    SYNTAX      DisplayString
    MAX-ACCESS  read-write
    STATUS      current
    DESCRIPTION
	"This is the first device."
    ::= { slave1Sensor 19}
	
slave1SensorHumidityOneMax OBJECT-TYPE
    SYNTAX      DisplayString
    MAX-ACCESS  read-write
    STATUS      current
    DESCRIPTION
	"This is the first device."
    ::= { slave1Sensor 20}

slave1SensorHumidityTwoMin OBJECT-TYPE
    SYNTAX      DisplayString
    MAX-ACCESS  read-write
    STATUS      current
    DESCRIPTION
	"This is the first device."
    ::= { slave1Sensor 21}
	
slave1SensorHumidityTwoMinCritical OBJECT-TYPE
    SYNTAX      DisplayString
    MAX-ACCESS  read-write
    STATUS      current
    DESCRIPTION
	"This is the first device."
    ::= { slave1Sensor 22}	
	
slave1SensorHumidityTwoMaxCritical OBJECT-TYPE
    SYNTAX      DisplayString
    MAX-ACCESS  read-write
    STATUS      current
    DESCRIPTION
	"This is the first device."
    ::= { slave1Sensor 23}
	
slave1SensorHumidityTwoMax OBJECT-TYPE
    SYNTAX      DisplayString
    MAX-ACCESS  read-write
    STATUS      current
    DESCRIPTION
	"This is the first device."
    ::= { slave1Sensor 24}
	
-------------------------------slave1 output name------------------------	
slave1OutputName OBJECT IDENTIFIER ::= { slave1 5}
slave1OutputNameOne OBJECT-TYPE
    SYNTAX      DisplayString
    MAX-ACCESS  read-write
    STATUS      current
    DESCRIPTION
	"The first output name of slave1"
    ::= { slave1OutputName 1}

slave1OutputNameTwo OBJECT-TYPE
    SYNTAX      DisplayString
    MAX-ACCESS  read-write
    STATUS      current
    DESCRIPTION
	"The second output name of slave1"
    ::= { slave1OutputName 2}

slave1OutputNameThree OBJECT-TYPE
    SYNTAX      DisplayString
    MAX-ACCESS  read-write
    STATUS      current
    DESCRIPTION
	"The second output name of slave1"
    ::= { slave1OutputName 3}

slave1OutputNameFour OBJECT-TYPE
    SYNTAX      DisplayString
    MAX-ACCESS  read-write
    STATUS      current
    DESCRIPTION
	"The second output name of slave1"
    ::= { slave1OutputName 4}

slave1OutputNameFive OBJECT-TYPE
    SYNTAX      DisplayString
    MAX-ACCESS  read-write
    STATUS      current
    DESCRIPTION
	"The second output name of slave1"
    ::= { slave1OutputName 5}

slave1OutputNameSix OBJECT-TYPE
    SYNTAX      DisplayString
    MAX-ACCESS  read-write
    STATUS      current
    DESCRIPTION
	"The second output name of slave1"
    ::= { slave1OutputName 6}

slave1OutputNameSeven OBJECT-TYPE
    SYNTAX      DisplayString
    MAX-ACCESS  read-write
    STATUS      current
    DESCRIPTION
	"The second output name of slave1"
    ::= { slave1OutputName 7}

slave1OutputNameEight OBJECT-TYPE
    SYNTAX      DisplayString
    MAX-ACCESS  read-write
    STATUS      current
    DESCRIPTION
	"The second output name of slave1"
    ::= { slave1OutputName 8}

slave1OutputNameNine OBJECT-TYPE
    SYNTAX      DisplayString
    MAX-ACCESS  read-write
    STATUS      current
    DESCRIPTION
	"The second output name of slave1"
    ::= { slave1OutputName 9}

slave1OutputNameTen OBJECT-TYPE
    SYNTAX      DisplayString
    MAX-ACCESS  read-write
    STATUS      current
    DESCRIPTION
	"The second output name of slave1"
    ::= { slave1OutputName 10}

slave1OutputNameEleven OBJECT-TYPE
    SYNTAX      DisplayString
    MAX-ACCESS  read-write
    STATUS      current
    DESCRIPTION
	"The second output name of slave1"
    ::= { slave1OutputName 11}

slave1OutputNameTwel OBJECT-TYPE
    SYNTAX      DisplayString
    MAX-ACCESS  read-write
    STATUS      current
    DESCRIPTION
	"The second output name of slave1"
    ::= { slave1OutputName 12}

slave1OutputNameThirteen OBJECT-TYPE
    SYNTAX      DisplayString
    MAX-ACCESS  read-write
    STATUS      current
    DESCRIPTION
	"The second output name of slave1"
    ::= { slave1OutputName 13}

slave1OutputNameFourteen OBJECT-TYPE
    SYNTAX      DisplayString
    MAX-ACCESS  read-write
    STATUS      current
    DESCRIPTION
	"The second output name of slave1"
    ::= { slave1OutputName 14}

slave1OutputNameFifteen OBJECT-TYPE
    SYNTAX      DisplayString
    MAX-ACCESS  read-write
    STATUS      current
    DESCRIPTION
	"The second output name of slave1"
    ::= { slave1OutputName 15}

slave1OutputNameSixteen OBJECT-TYPE
    SYNTAX      DisplayString
    MAX-ACCESS  read-write
    STATUS      current
    DESCRIPTION
	"The second output name of slave1"
    ::= { slave1OutputName 16}

slave1OutputNameSeventeen OBJECT-TYPE
    SYNTAX      DisplayString
    MAX-ACCESS  read-write
    STATUS      current
    DESCRIPTION
	"The second output name of slave1"
    ::= { slave1OutputName 17}

slave1OutputNameEighteen OBJECT-TYPE
    SYNTAX      DisplayString
    MAX-ACCESS  read-write
    STATUS      current
    DESCRIPTION
	"The second output name of slave1"
    ::= { slave1OutputName 18}
	
slave1OutputNameNineteen OBJECT-TYPE
    SYNTAX      DisplayString
    MAX-ACCESS  read-write
    STATUS      current
    DESCRIPTION
	"The second output name of slave1"
    ::= { slave1OutputName 19}
	
slave1OutputNametwenty OBJECT-TYPE
    SYNTAX      DisplayString
    MAX-ACCESS  read-write
    STATUS      current
    DESCRIPTION
	"The second output name of slave1"
    ::= { slave1OutputName 20}
	
slave1OutputNameTwentyone OBJECT-TYPE
    SYNTAX      DisplayString
    MAX-ACCESS  read-write
    STATUS      current
    DESCRIPTION
	"The second output name of slave1"
    ::= { slave1OutputName 21}
	
slave1OutputNameTwentyonetwo OBJECT-TYPE
    SYNTAX      DisplayString
    MAX-ACCESS  read-write
    STATUS      current
    DESCRIPTION
	"The second output name of slave1"
    ::= { slave1OutputName 22}
	
slave1OutputNameTwentythree OBJECT-TYPE
    SYNTAX      DisplayString
    MAX-ACCESS  read-write
    STATUS      current
    DESCRIPTION
	"The second output name of slave1"
    ::= { slave1OutputName 23}
	
slave1OutputNameTwentyfour OBJECT-TYPE
    SYNTAX      DisplayString
    MAX-ACCESS  read-write
    STATUS      current
    DESCRIPTION
	"The second output name of slave1"
    ::= { slave1OutputName 24}
	
slave1OutputNameTwentyfive OBJECT-TYPE
    SYNTAX      DisplayString
    MAX-ACCESS  read-write
    STATUS      current
    DESCRIPTION
	"The second output name of slave1"
    ::= { slave1OutputName 25}
	
slave1OutputNameTwentysix OBJECT-TYPE
    SYNTAX      DisplayString
    MAX-ACCESS  read-write
    STATUS      current
    DESCRIPTION
	"The second output name of slave1"
    ::= { slave1OutputName 26}
	
slave1OutputNameTwentyseven OBJECT-TYPE
    SYNTAX      DisplayString
    MAX-ACCESS  read-write
    STATUS      current
    DESCRIPTION
	"The second output name of slave1"
    ::= { slave1OutputName 27}
	
slave1OutputNameTwentyeight OBJECT-TYPE
    SYNTAX      DisplayString
    MAX-ACCESS  read-write
    STATUS      current
    DESCRIPTION
	"The second output name of slave1"
    ::= { slave1OutputName 28}	
slave1OutputNameTwentynine OBJECT-TYPE
    SYNTAX      DisplayString
    MAX-ACCESS  read-write
    STATUS      current
    DESCRIPTION
	"The second output name of slave1"
    ::= { slave1OutputName 29}
	
slave1OutputNameThirty OBJECT-TYPE
    SYNTAX      DisplayString
    MAX-ACCESS  read-write
    STATUS      current
    DESCRIPTION
	"The second output name of slave1"
    ::= { slave1OutputName 30}
	
slave1OutputNameThirtyone OBJECT-TYPE
    SYNTAX      DisplayString
    MAX-ACCESS  read-write
    STATUS      current
    DESCRIPTION
	"The second output name of slave1"
    ::= { slave1OutputName 31}
	
slave1OutputNameThirtytwo OBJECT-TYPE
    SYNTAX      DisplayString
    MAX-ACCESS  read-write
    STATUS      current
    DESCRIPTION
	"The second output name of slave1"
    ::= { slave1OutputName 32}
	
slave1OutputNameThirtythree OBJECT-TYPE
    SYNTAX      DisplayString
    MAX-ACCESS  read-write
    STATUS      current
    DESCRIPTION
	"The second output name of slave1"
    ::= { slave1OutputName 33}
	
slave1OutputNameThirtyfour OBJECT-TYPE
    SYNTAX      DisplayString
    MAX-ACCESS  read-write
    STATUS      current
    DESCRIPTION
	"The second output name of slave1"
    ::= { slave1OutputName 34}
	
slave1OutputNameThirtyfive OBJECT-TYPE
    SYNTAX      DisplayString
    MAX-ACCESS  read-write
    STATUS      current
    DESCRIPTION
	"The second output name of slave1"
    ::= { slave1OutputName 35}
	
slave1OutputNameThirtysix OBJECT-TYPE
    SYNTAX      DisplayString
    MAX-ACCESS  read-write
    STATUS      current
    DESCRIPTION
	"The second output name of slave1"
    ::= { slave1OutputName 36}
	
slave1OutputNameThirtyseven OBJECT-TYPE
    SYNTAX      DisplayString
    MAX-ACCESS  read-write
    STATUS      current
    DESCRIPTION
	"The second output name of slave1"
    ::= { slave1OutputName 37}
	
slave1OutputNameThirtyeight OBJECT-TYPE
    SYNTAX      DisplayString
    MAX-ACCESS  read-write
    STATUS      current
    DESCRIPTION
	"The second output name of slave1"
    ::= { slave1OutputName 38}
	
slave1OutputNameThirtynine OBJECT-TYPE
    SYNTAX      DisplayString
    MAX-ACCESS  read-write
    STATUS      current
    DESCRIPTION
	"The second output name of slave1"
    ::= { slave1OutputName 39}
	
slave1OutputNameFourty OBJECT-TYPE
    SYNTAX      DisplayString
    MAX-ACCESS  read-write
    STATUS      current
    DESCRIPTION
	"The second output name of slave1"
    ::= { slave1OutputName 40}
	
slave1OutputNameFourtyone OBJECT-TYPE
    SYNTAX      DisplayString
    MAX-ACCESS  read-write
    STATUS      current
    DESCRIPTION
	"The second output name of slave1"
    ::= { slave1OutputName 41}
	
slave1OutputNameFourtytwo OBJECT-TYPE
    SYNTAX      DisplayString
    MAX-ACCESS  read-write
    STATUS      current
    DESCRIPTION
	"The second output name of slave1"
    ::= { slave1OutputName 42}	

	
-------------------------------slave1 output delay------------------------	
slave1OutputDelay OBJECT IDENTIFIER ::= { slave1 6}	
slave1OutputDelayOne OBJECT-TYPE
    SYNTAX      DisplayString
    MAX-ACCESS  read-write
    STATUS      current
    DESCRIPTION
	"The first output name of slave1"
    ::= { slave1OutputDelay 1}

slave1OutputDelayTwo OBJECT-TYPE
    SYNTAX      DisplayString
    MAX-ACCESS  read-write
    STATUS      current
    DESCRIPTION
	"The second output name of slave1"
    ::= { slave1OutputDelay 2}

slave1OutputDelayThree OBJECT-TYPE
    SYNTAX      DisplayString
    MAX-ACCESS  read-write
    STATUS      current
    DESCRIPTION
	"The second output name of slave1"
    ::= { slave1OutputDelay 3}

slave1OutputDelayFour OBJECT-TYPE
    SYNTAX      DisplayString
    MAX-ACCESS  read-write
    STATUS      current
    DESCRIPTION
	"The second output name of slave1"
    ::= { slave1OutputDelay 4}

slave1OutputDelayFive OBJECT-TYPE
    SYNTAX      DisplayString
    MAX-ACCESS  read-write
    STATUS      current
    DESCRIPTION
	"The second output name of slave1"
    ::= { slave1OutputDelay 5}

slave1OutputDelaySix OBJECT-TYPE
    SYNTAX      DisplayString
    MAX-ACCESS  read-write
    STATUS      current
    DESCRIPTION
	"The second output name of slave1"
    ::= { slave1OutputDelay 6}

slave1OutputDelaySeven OBJECT-TYPE
    SYNTAX      DisplayString
    MAX-ACCESS  read-write
    STATUS      current
    DESCRIPTION
	"The second output name of slave1"
    ::= { slave1OutputDelay 7}

slave1OutputDelayEight OBJECT-TYPE
    SYNTAX      DisplayString
    MAX-ACCESS  read-write
    STATUS      current
    DESCRIPTION
	"The second output name of slave1"
    ::= { slave1OutputDelay 8}

slave1OutputDelayNine OBJECT-TYPE
    SYNTAX      DisplayString
    MAX-ACCESS  read-write
    STATUS      current
    DESCRIPTION
	"The second output name of slave1"
    ::= { slave1OutputDelay 9}

slave1OutputDelayTen OBJECT-TYPE
    SYNTAX      DisplayString
    MAX-ACCESS  read-write
    STATUS      current
    DESCRIPTION
	"The second output name of slave1"
    ::= { slave1OutputDelay 10}

slave1OutputDelayEleven OBJECT-TYPE
    SYNTAX      DisplayString
    MAX-ACCESS  read-write
    STATUS      current
    DESCRIPTION
	"The second output name of slave1"
    ::= { slave1OutputDelay 11}

slave1OutputDelayTwel OBJECT-TYPE
    SYNTAX      DisplayString
    MAX-ACCESS  read-write
    STATUS      current
    DESCRIPTION
	"The second output name of slave1"
    ::= { slave1OutputDelay 12}

slave1OutputDelayThirteen OBJECT-TYPE
    SYNTAX      DisplayString
    MAX-ACCESS  read-write
    STATUS      current
    DESCRIPTION
	"The second output name of slave1"
    ::= { slave1OutputDelay 13}

slave1OutputDelayFourteen OBJECT-TYPE
    SYNTAX      DisplayString
    MAX-ACCESS  read-write
    STATUS      current
    DESCRIPTION
	"The second output name of slave1"
    ::= { slave1OutputDelay 14}

slave1OutputDelayFifteen OBJECT-TYPE
    SYNTAX      DisplayString
    MAX-ACCESS  read-write
    STATUS      current
    DESCRIPTION
	"The second output name of slave1"
    ::= { slave1OutputDelay 15}

slave1OutputDelaySixteen OBJECT-TYPE
    SYNTAX      DisplayString
    MAX-ACCESS  read-write
    STATUS      current
    DESCRIPTION
	"The second output name of slave1"
    ::= { slave1OutputDelay 16}

slave1OutputDelaySeventeen OBJECT-TYPE
    SYNTAX      DisplayString
    MAX-ACCESS  read-write
    STATUS      current
    DESCRIPTION
	"The second output name of slave1"
    ::= { slave1OutputDelay 17}

slave1OutputDelayEighteen OBJECT-TYPE
    SYNTAX      DisplayString
    MAX-ACCESS  read-write
    STATUS      current
    DESCRIPTION
	"The second output name of slave1"
    ::= { slave1OutputDelay 18}
	
slave1OutputDelayNineteen OBJECT-TYPE
    SYNTAX      DisplayString
    MAX-ACCESS  read-write
    STATUS      current
    DESCRIPTION
	"The second output name of slave1"
    ::= { slave1OutputDelay 19}
	
slave1OutputDelaytwenty OBJECT-TYPE
    SYNTAX      DisplayString
    MAX-ACCESS  read-write
    STATUS      current
    DESCRIPTION
	"The second output name of slave1"
    ::= { slave1OutputDelay 20}
	
slave1OutputDelayTwentyone OBJECT-TYPE
    SYNTAX      DisplayString
    MAX-ACCESS  read-write
    STATUS      current
    DESCRIPTION
	"The second output name of slave1"
    ::= { slave1OutputDelay 21}
	
slave1OutputDelayTwentyonetwo OBJECT-TYPE
    SYNTAX      DisplayString
    MAX-ACCESS  read-write
    STATUS      current
    DESCRIPTION
	"The second output name of slave1"
    ::= { slave1OutputDelay 22}
	
slave1OutputDelayTwentythree OBJECT-TYPE
    SYNTAX      DisplayString
    MAX-ACCESS  read-write
    STATUS      current
    DESCRIPTION
	"The second output name of slave1"
    ::= { slave1OutputDelay 23}
	
slave1OutputDelayTwentyfour OBJECT-TYPE
    SYNTAX      DisplayString
    MAX-ACCESS  read-write
    STATUS      current
    DESCRIPTION
	"The second output name of slave1"
    ::= { slave1OutputDelay 24}
	
slave1OutputDelayTwentyfive OBJECT-TYPE
    SYNTAX      DisplayString
    MAX-ACCESS  read-write
    STATUS      current
    DESCRIPTION
	"The second output name of slave1"
    ::= { slave1OutputDelay 25}
	
slave1OutputDelayTwentysix OBJECT-TYPE
    SYNTAX      DisplayString
    MAX-ACCESS  read-write
    STATUS      current
    DESCRIPTION
	"The second output name of slave1"
    ::= { slave1OutputDelay 26}
	
slave1OutputDelayTwentyseven OBJECT-TYPE
    SYNTAX      DisplayString
    MAX-ACCESS  read-write
    STATUS      current
    DESCRIPTION
	"The second output name of slave1"
    ::= { slave1OutputDelay 27}
	
slave1OutputDelayTwentyeight OBJECT-TYPE
    SYNTAX      DisplayString
    MAX-ACCESS  read-write
    STATUS      current
    DESCRIPTION
	"The second output name of slave1"
    ::= { slave1OutputDelay 28}	
slave1OutputDelayTwentynine OBJECT-TYPE
    SYNTAX      DisplayString
    MAX-ACCESS  read-write
    STATUS      current
    DESCRIPTION
	"The second output name of slave1"
    ::= { slave1OutputDelay 29}
	
slave1OutputDelayThirty OBJECT-TYPE
    SYNTAX      DisplayString
    MAX-ACCESS  read-write
    STATUS      current
    DESCRIPTION
	"The second output name of slave1"
    ::= { slave1OutputDelay 30}
	
slave1OutputDelayThirtyone OBJECT-TYPE
    SYNTAX      DisplayString
    MAX-ACCESS  read-write
    STATUS      current
    DESCRIPTION
	"The second output name of slave1"
    ::= { slave1OutputDelay 31}
	
slave1OutputDelayThirtytwo OBJECT-TYPE
    SYNTAX      DisplayString
    MAX-ACCESS  read-write
    STATUS      current
    DESCRIPTION
	"The second output name of slave1"
    ::= { slave1OutputDelay 32}
	
slave1OutputDelayThirtythree OBJECT-TYPE
    SYNTAX      DisplayString
    MAX-ACCESS  read-write
    STATUS      current
    DESCRIPTION
	"The second output name of slave1"
    ::= { slave1OutputDelay 33}
	
slave1OutputDelayThirtyfour OBJECT-TYPE
    SYNTAX      DisplayString
    MAX-ACCESS  read-write
    STATUS      current
    DESCRIPTION
	"The second output name of slave1"
    ::= { slave1OutputDelay 34}
	
slave1OutputDelayThirtyfive OBJECT-TYPE
    SYNTAX      DisplayString
    MAX-ACCESS  read-write
    STATUS      current
    DESCRIPTION
	"The second output name of slave1"
    ::= { slave1OutputDelay 35}
	
slave1OutputDelayThirtysix OBJECT-TYPE
    SYNTAX      DisplayString
    MAX-ACCESS  read-write
    STATUS      current
    DESCRIPTION
	"The second output name of slave1"
    ::= { slave1OutputDelay 36}
	
slave1OutputDelayThirtyseven OBJECT-TYPE
    SYNTAX      DisplayString
    MAX-ACCESS  read-write
    STATUS      current
    DESCRIPTION
	"The second output name of slave1"
    ::= { slave1OutputDelay 37}
	
slave1OutputDelayThirtyeight OBJECT-TYPE
    SYNTAX      DisplayString
    MAX-ACCESS  read-write
    STATUS      current
    DESCRIPTION
	"The second output name of slave1"
    ::= { slave1OutputDelay 38}
	
slave1OutputDelayThirtynine OBJECT-TYPE
    SYNTAX      DisplayString
    MAX-ACCESS  read-write
    STATUS      current
    DESCRIPTION
	"The second output name of slave1"
    ::= { slave1OutputDelay 39}
	
slave1OutputDelayFourty OBJECT-TYPE
    SYNTAX      DisplayString
    MAX-ACCESS  read-write
    STATUS      current
    DESCRIPTION
	"The second output name of slave1"
    ::= { slave1OutputDelay 40}
	
slave1OutputDelayFourtyone OBJECT-TYPE
    SYNTAX      DisplayString
    MAX-ACCESS  read-write
    STATUS      current
    DESCRIPTION
	"The second output name of slave1"
    ::= { slave1OutputDelay 41}
	
slave1OutputDelayFourtytwo OBJECT-TYPE
    SYNTAX      DisplayString
    MAX-ACCESS  read-write
    STATUS      current
    DESCRIPTION
	"The second output name of slave1"
    ::= { slave1OutputDelay 42}

	
-------------------------------slave1 output switch------------------------	
slave1OutputSwitch OBJECT IDENTIFIER ::= { slave1 7}		
slave1OutputSwitchOne OBJECT-TYPE
    SYNTAX      DisplayString
    MAX-ACCESS  read-write
    STATUS      current
    DESCRIPTION
	"The first output name of slave1"
    ::= { slave1OutputSwitch 1}

slave1OutputSwitchTwo OBJECT-TYPE
    SYNTAX      DisplayString
    MAX-ACCESS  read-write
    STATUS      current
    DESCRIPTION
	"The second output name of slave1"
    ::= { slave1OutputSwitch 2}

slave1OutputSwitchThree OBJECT-TYPE
    SYNTAX      DisplayString
    MAX-ACCESS  read-write
    STATUS      current
    DESCRIPTION
	"The second output name of slave1"
    ::= { slave1OutputSwitch 3}

slave1OutputSwitchFour OBJECT-TYPE
    SYNTAX      DisplayString
    MAX-ACCESS  read-write
    STATUS      current
    DESCRIPTION
	"The second output name of slave1"
    ::= { slave1OutputSwitch 4}

slave1OutputSwitchFive OBJECT-TYPE
    SYNTAX      DisplayString
    MAX-ACCESS  read-write
    STATUS      current
    DESCRIPTION
	"The second output name of slave1"
    ::= { slave1OutputSwitch 5}

slave1OutputSwitchSix OBJECT-TYPE
    SYNTAX      DisplayString
    MAX-ACCESS  read-write
    STATUS      current
    DESCRIPTION
	"The second output name of slave1"
    ::= { slave1OutputSwitch 6}

slave1OutputSwitchSeven OBJECT-TYPE
    SYNTAX      DisplayString
    MAX-ACCESS  read-write
    STATUS      current
    DESCRIPTION
	"The second output name of slave1"
    ::= { slave1OutputSwitch 7}

slave1OutputSwitchEight OBJECT-TYPE
    SYNTAX      DisplayString
    MAX-ACCESS  read-write
    STATUS      current
    DESCRIPTION
	"The second output name of slave1"
    ::= { slave1OutputSwitch 8}

slave1OutputSwitchNine OBJECT-TYPE
    SYNTAX      DisplayString
    MAX-ACCESS  read-write
    STATUS      current
    DESCRIPTION
	"The second output name of slave1"
    ::= { slave1OutputSwitch 9}

slave1OutputSwitchTen OBJECT-TYPE
    SYNTAX      DisplayString
    MAX-ACCESS  read-write
    STATUS      current
    DESCRIPTION
	"The second output name of slave1"
    ::= { slave1OutputSwitch 10}

slave1OutputSwitchEleven OBJECT-TYPE
    SYNTAX      DisplayString
    MAX-ACCESS  read-write
    STATUS      current
    DESCRIPTION
	"The second output name of slave1"
    ::= { slave1OutputSwitch 11}

slave1OutputSwitchTwel OBJECT-TYPE
    SYNTAX      DisplayString
    MAX-ACCESS  read-write
    STATUS      current
    DESCRIPTION
	"The second output name of slave1"
    ::= { slave1OutputSwitch 12}

slave1OutputSwitchThirteen OBJECT-TYPE
    SYNTAX      DisplayString
    MAX-ACCESS  read-write
    STATUS      current
    DESCRIPTION
	"The second output name of slave1"
    ::= { slave1OutputSwitch 13}

slave1OutputSwitchFourteen OBJECT-TYPE
    SYNTAX      DisplayString
    MAX-ACCESS  read-write
    STATUS      current
    DESCRIPTION
	"The second output name of slave1"
    ::= { slave1OutputSwitch 14}

slave1OutputSwitchFifteen OBJECT-TYPE
    SYNTAX      DisplayString
    MAX-ACCESS  read-write
    STATUS      current
    DESCRIPTION
	"The second output name of slave1"
    ::= { slave1OutputSwitch 15}

slave1OutputSwitchSixteen OBJECT-TYPE
    SYNTAX      DisplayString
    MAX-ACCESS  read-write
    STATUS      current
    DESCRIPTION
	"The second output name of slave1"
    ::= { slave1OutputSwitch 16}

slave1OutputSwitchSeventeen OBJECT-TYPE
    SYNTAX      DisplayString
    MAX-ACCESS  read-write
    STATUS      current
    DESCRIPTION
	"The second output name of slave1"
    ::= { slave1OutputSwitch 17}

slave1OutputSwitchEighteen OBJECT-TYPE
    SYNTAX      DisplayString
    MAX-ACCESS  read-write
    STATUS      current
    DESCRIPTION
	"The second output name of slave1"
    ::= { slave1OutputSwitch 18}
	
slave1OutputSwitchNineteen OBJECT-TYPE
    SYNTAX      DisplayString
    MAX-ACCESS  read-write
    STATUS      current
    DESCRIPTION
	"The second output name of slave1"
    ::= { slave1OutputSwitch 19}
	
slave1OutputSwitchtwenty OBJECT-TYPE
    SYNTAX      DisplayString
    MAX-ACCESS  read-write
    STATUS      current
    DESCRIPTION
	"The second output name of slave1"
    ::= { slave1OutputSwitch 20}
	
slave1OutputSwitchTwentyone OBJECT-TYPE
    SYNTAX      DisplayString
    MAX-ACCESS  read-write
    STATUS      current
    DESCRIPTION
	"The second output name of slave1"
    ::= { slave1OutputSwitch 21}
	
slave1OutputSwitchTwentyonetwo OBJECT-TYPE
    SYNTAX      DisplayString
    MAX-ACCESS  read-write
    STATUS      current
    DESCRIPTION
	"The second output name of slave1"
    ::= { slave1OutputSwitch 22}
	
slave1OutputSwitchTwentythree OBJECT-TYPE
    SYNTAX      DisplayString
    MAX-ACCESS  read-write
    STATUS      current
    DESCRIPTION
	"The second output name of slave1"
    ::= { slave1OutputSwitch 23}
	
slave1OutputSwitchTwentyfour OBJECT-TYPE
    SYNTAX      DisplayString
    MAX-ACCESS  read-write
    STATUS      current
    DESCRIPTION
	"The second output name of slave1"
    ::= { slave1OutputSwitch 24}
	
slave1OutputSwitchTwentyfive OBJECT-TYPE
    SYNTAX      DisplayString
    MAX-ACCESS  read-write
    STATUS      current
    DESCRIPTION
	"The second output name of slave1"
    ::= { slave1OutputSwitch 25}
	
slave1OutputSwitchTwentysix OBJECT-TYPE
    SYNTAX      DisplayString
    MAX-ACCESS  read-write
    STATUS      current
    DESCRIPTION
	"The second output name of slave1"
    ::= { slave1OutputSwitch 26}
	
slave1OutputSwitchTwentyseven OBJECT-TYPE
    SYNTAX      DisplayString
    MAX-ACCESS  read-write
    STATUS      current
    DESCRIPTION
	"The second output name of slave1"
    ::= { slave1OutputSwitch 27}
	
slave1OutputSwitchTwentyeight OBJECT-TYPE
    SYNTAX      DisplayString
    MAX-ACCESS  read-write
    STATUS      current
    DESCRIPTION
	"The second output name of slave1"
    ::= { slave1OutputSwitch 28}	
slave1OutputSwitchTwentynine OBJECT-TYPE
    SYNTAX      DisplayString
    MAX-ACCESS  read-write
    STATUS      current
    DESCRIPTION
	"The second output name of slave1"
    ::= { slave1OutputSwitch 29}
	
slave1OutputSwitchThirty OBJECT-TYPE
    SYNTAX      DisplayString
    MAX-ACCESS  read-write
    STATUS      current
    DESCRIPTION
	"The second output name of slave1"
    ::= { slave1OutputSwitch 30}
	
slave1OutputSwitchThirtyone OBJECT-TYPE
    SYNTAX      DisplayString
    MAX-ACCESS  read-write
    STATUS      current
    DESCRIPTION
	"The second output name of slave1"
    ::= { slave1OutputSwitch 31}
	
slave1OutputSwitchThirtytwo OBJECT-TYPE
    SYNTAX      DisplayString
    MAX-ACCESS  read-write
    STATUS      current
    DESCRIPTION
	"The second output name of slave1"
    ::= { slave1OutputSwitch 32}
	
slave1OutputSwitchThirtythree OBJECT-TYPE
    SYNTAX      DisplayString
    MAX-ACCESS  read-write
    STATUS      current
    DESCRIPTION
	"The second output name of slave1"
    ::= { slave1OutputSwitch 33}
	
slave1OutputSwitchThirtyfour OBJECT-TYPE
    SYNTAX      DisplayString
    MAX-ACCESS  read-write
    STATUS      current
    DESCRIPTION
	"The second output name of slave1"
    ::= { slave1OutputSwitch 34}
	
slave1OutputSwitchThirtyfive OBJECT-TYPE
    SYNTAX      DisplayString
    MAX-ACCESS  read-write
    STATUS      current
    DESCRIPTION
	"The second output name of slave1"
    ::= { slave1OutputSwitch 35}
	
slave1OutputSwitchThirtysix OBJECT-TYPE
    SYNTAX      DisplayString
    MAX-ACCESS  read-write
    STATUS      current
    DESCRIPTION
	"The second output name of slave1"
    ::= { slave1OutputSwitch 36}
	
slave1OutputSwitchThirtyseven OBJECT-TYPE
    SYNTAX      DisplayString
    MAX-ACCESS  read-write
    STATUS      current
    DESCRIPTION
	"The second output name of slave1"
    ::= { slave1OutputSwitch 37}
	
slave1OutputSwitchThirtyeight OBJECT-TYPE
    SYNTAX      DisplayString
    MAX-ACCESS  read-write
    STATUS      current
    DESCRIPTION
	"The second output name of slave1"
    ::= { slave1OutputSwitch 38}
	
slave1OutputSwitchThirtynine OBJECT-TYPE
    SYNTAX      DisplayString
    MAX-ACCESS  read-write
    STATUS      current
    DESCRIPTION
	"The second output name of slave1"
    ::= { slave1OutputSwitch 39}
	
slave1OutputSwitchFourty OBJECT-TYPE
    SYNTAX      DisplayString
    MAX-ACCESS  read-write
    STATUS      current
    DESCRIPTION
	"The second output name of slave1"
    ::= { slave1OutputSwitch 40}
	
slave1OutputSwitchFourtyone OBJECT-TYPE
    SYNTAX      DisplayString
    MAX-ACCESS  read-write
    STATUS      current
    DESCRIPTION
	"The second output name of slave1"
    ::= { slave1OutputSwitch 41}
	
slave1OutputSwitchFourtytwo OBJECT-TYPE
    SYNTAX      DisplayString
    MAX-ACCESS  read-write
    STATUS      current
    DESCRIPTION
	"The second output name of slave1"
    ::= { slave1OutputSwitch 42}

	
-------------------------------slave1 output current------------------------	
slave1OutputCurrent OBJECT IDENTIFIER ::= { slave1 8}		
slave1OutputCurrentValue OBJECT IDENTIFIER ::= { slave1OutputCurrent 1}	

slave1OutputCurrentValueOne OBJECT-TYPE
    SYNTAX      DisplayString
    MAX-ACCESS  read-write
    STATUS      current
    DESCRIPTION
	"The first output name of slave1"
    ::= { slave1OutputCurrentValue 1}

slave1OutputCurrentValueTwo OBJECT-TYPE
    SYNTAX      DisplayString
    MAX-ACCESS  read-write
    STATUS      current
    DESCRIPTION
	"The second output name of slave1"
    ::= { slave1OutputCurrentValue 2}

slave1OutputCurrentValueThree OBJECT-TYPE
    SYNTAX      DisplayString
    MAX-ACCESS  read-write
    STATUS      current
    DESCRIPTION
	"The second output name of slave1"
    ::= { slave1OutputCurrentValue 3}

slave1OutputCurrentValueFour OBJECT-TYPE
    SYNTAX      DisplayString
    MAX-ACCESS  read-write
    STATUS      current
    DESCRIPTION
	"The second output name of slave1"
    ::= { slave1OutputCurrentValue 4}

slave1OutputCurrentValueFive OBJECT-TYPE
    SYNTAX      DisplayString
    MAX-ACCESS  read-write
    STATUS      current
    DESCRIPTION
	"The second output name of slave1"
    ::= { slave1OutputCurrentValue 5}

slave1OutputCurrentValueSix OBJECT-TYPE
    SYNTAX      DisplayString
    MAX-ACCESS  read-write
    STATUS      current
    DESCRIPTION
	"The second output name of slave1"
    ::= { slave1OutputCurrentValue 6}

slave1OutputCurrentValueSeven OBJECT-TYPE
    SYNTAX      DisplayString
    MAX-ACCESS  read-write
    STATUS      current
    DESCRIPTION
	"The second output name of slave1"
    ::= { slave1OutputCurrentValue 7}

slave1OutputCurrentValueEight OBJECT-TYPE
    SYNTAX      DisplayString
    MAX-ACCESS  read-write
    STATUS      current
    DESCRIPTION
	"The second output name of slave1"
    ::= { slave1OutputCurrentValue 8}

slave1OutputCurrentValueNine OBJECT-TYPE
    SYNTAX      DisplayString
    MAX-ACCESS  read-write
    STATUS      current
    DESCRIPTION
	"The second output name of slave1"
    ::= { slave1OutputCurrentValue 9}

slave1OutputCurrentValueTen OBJECT-TYPE
    SYNTAX      DisplayString
    MAX-ACCESS  read-write
    STATUS      current
    DESCRIPTION
	"The second output name of slave1"
    ::= { slave1OutputCurrentValue 10}

slave1OutputCurrentValueEleven OBJECT-TYPE
    SYNTAX      DisplayString
    MAX-ACCESS  read-write
    STATUS      current
    DESCRIPTION
	"The second output name of slave1"
    ::= { slave1OutputCurrentValue 11}

slave1OutputCurrentValueTwel OBJECT-TYPE
    SYNTAX      DisplayString
    MAX-ACCESS  read-write
    STATUS      current
    DESCRIPTION
	"The second output name of slave1"
    ::= { slave1OutputCurrentValue 12}

slave1OutputCurrentValueThirteen OBJECT-TYPE
    SYNTAX      DisplayString
    MAX-ACCESS  read-write
    STATUS      current
    DESCRIPTION
	"The second output name of slave1"
    ::= { slave1OutputCurrentValue 13}

slave1OutputCurrentValueFourteen OBJECT-TYPE
    SYNTAX      DisplayString
    MAX-ACCESS  read-write
    STATUS      current
    DESCRIPTION
	"The second output name of slave1"
    ::= { slave1OutputCurrentValue 14}

slave1OutputCurrentValueFifteen OBJECT-TYPE
    SYNTAX      DisplayString
    MAX-ACCESS  read-write
    STATUS      current
    DESCRIPTION
	"The second output name of slave1"
    ::= { slave1OutputCurrentValue 15}

slave1OutputCurrentValueSixteen OBJECT-TYPE
    SYNTAX      DisplayString
    MAX-ACCESS  read-write
    STATUS      current
    DESCRIPTION
	"The second output name of slave1"
    ::= { slave1OutputCurrentValue 16}

slave1OutputCurrentValueSeventeen OBJECT-TYPE
    SYNTAX      DisplayString
    MAX-ACCESS  read-write
    STATUS      current
    DESCRIPTION
	"The second output name of slave1"
    ::= { slave1OutputCurrentValue 17}

slave1OutputCurrentValueEighteen OBJECT-TYPE
    SYNTAX      DisplayString
    MAX-ACCESS  read-write
    STATUS      current
    DESCRIPTION
	"The second output name of slave1"
    ::= { slave1OutputCurrentValue 18}
	
slave1OutputCurrentValueNineteen OBJECT-TYPE
    SYNTAX      DisplayString
    MAX-ACCESS  read-write
    STATUS      current
    DESCRIPTION
	"The second output name of slave1"
    ::= { slave1OutputCurrentValue 19}
	
slave1OutputCurrentValuetwenty OBJECT-TYPE
    SYNTAX      DisplayString
    MAX-ACCESS  read-write
    STATUS      current
    DESCRIPTION
	"The second output name of slave1"
    ::= { slave1OutputCurrentValue 20}
	
slave1OutputCurrentValueTwentyone OBJECT-TYPE
    SYNTAX      DisplayString
    MAX-ACCESS  read-write
    STATUS      current
    DESCRIPTION
	"The second output name of slave1"
    ::= { slave1OutputCurrentValue 21}
	
slave1OutputCurrentValueTwentyonetwo OBJECT-TYPE
    SYNTAX      DisplayString
    MAX-ACCESS  read-write
    STATUS      current
    DESCRIPTION
	"The second output name of slave1"
    ::= { slave1OutputCurrentValue 22}
	
slave1OutputCurrentValueTwentythree OBJECT-TYPE
    SYNTAX      DisplayString
    MAX-ACCESS  read-write
    STATUS      current
    DESCRIPTION
	"The second output name of slave1"
    ::= { slave1OutputCurrentValue 23}
	
slave1OutputCurrentValueTwentyfour OBJECT-TYPE
    SYNTAX      DisplayString
    MAX-ACCESS  read-write
    STATUS      current
    DESCRIPTION
	"The second output name of slave1"
    ::= { slave1OutputCurrentValue 24}
	
slave1OutputCurrentValueTwentyfive OBJECT-TYPE
    SYNTAX      DisplayString
    MAX-ACCESS  read-write
    STATUS      current
    DESCRIPTION
	"The second output name of slave1"
    ::= { slave1OutputCurrentValue 25}
	
slave1OutputCurrentValueTwentysix OBJECT-TYPE
    SYNTAX      DisplayString
    MAX-ACCESS  read-write
    STATUS      current
    DESCRIPTION
	"The second output name of slave1"
    ::= { slave1OutputCurrentValue 26}
	
slave1OutputCurrentValueTwentyseven OBJECT-TYPE
    SYNTAX      DisplayString
    MAX-ACCESS  read-write
    STATUS      current
    DESCRIPTION
	"The second output name of slave1"
    ::= { slave1OutputCurrentValue 27}
	
slave1OutputCurrentValueTwentyeight OBJECT-TYPE
    SYNTAX      DisplayString
    MAX-ACCESS  read-write
    STATUS      current
    DESCRIPTION
	"The second output name of slave1"
    ::= { slave1OutputCurrentValue 28}	
slave1OutputCurrentValueTwentynine OBJECT-TYPE
    SYNTAX      DisplayString
    MAX-ACCESS  read-write
    STATUS      current
    DESCRIPTION
	"The second output name of slave1"
    ::= { slave1OutputCurrentValue 29}
	
slave1OutputCurrentValueThirty OBJECT-TYPE
    SYNTAX      DisplayString
    MAX-ACCESS  read-write
    STATUS      current
    DESCRIPTION
	"The second output name of slave1"
    ::= { slave1OutputCurrentValue 30}
	
slave1OutputCurrentValueThirtyone OBJECT-TYPE
    SYNTAX      DisplayString
    MAX-ACCESS  read-write
    STATUS      current
    DESCRIPTION
	"The second output name of slave1"
    ::= { slave1OutputCurrentValue 31}
	
slave1OutputCurrentValueThirtytwo OBJECT-TYPE
    SYNTAX      DisplayString
    MAX-ACCESS  read-write
    STATUS      current
    DESCRIPTION
	"The second output name of slave1"
    ::= { slave1OutputCurrentValue 32}
	
slave1OutputCurrentValueThirtythree OBJECT-TYPE
    SYNTAX      DisplayString
    MAX-ACCESS  read-write
    STATUS      current
    DESCRIPTION
	"The second output name of slave1"
    ::= { slave1OutputCurrentValue 33}
	
slave1OutputCurrentValueThirtyfour OBJECT-TYPE
    SYNTAX      DisplayString
    MAX-ACCESS  read-write
    STATUS      current
    DESCRIPTION
	"The second output name of slave1"
    ::= { slave1OutputCurrentValue 34}
	
slave1OutputCurrentValueThirtyfive OBJECT-TYPE
    SYNTAX      DisplayString
    MAX-ACCESS  read-write
    STATUS      current
    DESCRIPTION
	"The second output name of slave1"
    ::= { slave1OutputCurrentValue 35}
	
slave1OutputCurrentValueThirtysix OBJECT-TYPE
    SYNTAX      DisplayString
    MAX-ACCESS  read-write
    STATUS      current
    DESCRIPTION
	"The second output name of slave1"
    ::= { slave1OutputCurrentValue 36}
	
slave1OutputCurrentValueThirtyseven OBJECT-TYPE
    SYNTAX      DisplayString
    MAX-ACCESS  read-write
    STATUS      current
    DESCRIPTION
	"The second output name of slave1"
    ::= { slave1OutputCurrentValue 37}
	
slave1OutputCurrentValueThirtyeight OBJECT-TYPE
    SYNTAX      DisplayString
    MAX-ACCESS  read-write
    STATUS      current
    DESCRIPTION
	"The second output name of slave1"
    ::= { slave1OutputCurrentValue 38}
	
slave1OutputCurrentValueThirtynine OBJECT-TYPE
    SYNTAX      DisplayString
    MAX-ACCESS  read-write
    STATUS      current
    DESCRIPTION
	"The second output name of slave1"
    ::= { slave1OutputCurrentValue 39}
	
slave1OutputCurrentValueFourty OBJECT-TYPE
    SYNTAX      DisplayString
    MAX-ACCESS  read-write
    STATUS      current
    DESCRIPTION
	"The second output name of slave1"
    ::= { slave1OutputCurrentValue 40}
	
slave1OutputCurrentValueFourtyone OBJECT-TYPE
    SYNTAX      DisplayString
    MAX-ACCESS  read-write
    STATUS      current
    DESCRIPTION
	"The second output name of slave1"
    ::= { slave1OutputCurrentValue 41}
	
slave1OutputCurrentValueFourtytwo OBJECT-TYPE
    SYNTAX      DisplayString
    MAX-ACCESS  read-write
    STATUS      current
    DESCRIPTION
	"The second output name of slave1"
    ::= { slave1OutputCurrentValue 42}


-------------------------------slave1 output current Min------------------------			
slave1OutputCurrentMin OBJECT IDENTIFIER ::= { slave1OutputCurrent 2}	

slave1OutputCurrentMinOne OBJECT-TYPE
    SYNTAX      DisplayString
    MAX-ACCESS  read-write
    STATUS      current
    DESCRIPTION
	"The first output Min. current alarm value of slave1"
    ::= { slave1OutputCurrentMin 1}

slave1OutputCurrentMinTwo OBJECT-TYPE
    SYNTAX      DisplayString
    MAX-ACCESS  read-write
    STATUS      current
    DESCRIPTION
	"The second output Min. current alarm value of slave1"
    ::= { slave1OutputCurrentMin 2}

slave1OutputCurrentMinThree OBJECT-TYPE
    SYNTAX      DisplayString
    MAX-ACCESS  read-write
    STATUS      current
    DESCRIPTION
	"The second output Min. current alarm value of slave1"
    ::= { slave1OutputCurrentMin 3}

slave1OutputCurrentMinFour OBJECT-TYPE
    SYNTAX      DisplayString
    MAX-ACCESS  read-write
    STATUS      current
    DESCRIPTION
	"The second output Min. current alarm value of slave1"
    ::= { slave1OutputCurrentMin 4}

slave1OutputCurrentMinFive OBJECT-TYPE
    SYNTAX      DisplayString
    MAX-ACCESS  read-write
    STATUS      current
    DESCRIPTION
	"The second output Min. current alarm value of slave1"
    ::= { slave1OutputCurrentMin 5}

slave1OutputCurrentMinSix OBJECT-TYPE
    SYNTAX      DisplayString
    MAX-ACCESS  read-write
    STATUS      current
    DESCRIPTION
	"The second output Min. current alarm value of slave1"
    ::= { slave1OutputCurrentMin 6}

slave1OutputCurrentMinSeven OBJECT-TYPE
    SYNTAX      DisplayString
    MAX-ACCESS  read-write
    STATUS      current
    DESCRIPTION
	"The second output Min. current alarm value of slave1"
    ::= { slave1OutputCurrentMin 7}

slave1OutputCurrentMinEight OBJECT-TYPE
    SYNTAX      DisplayString
    MAX-ACCESS  read-write
    STATUS      current
    DESCRIPTION
	"The second output Min. current alarm value of slave1"
    ::= { slave1OutputCurrentMin 8}

slave1OutputCurrentMinNine OBJECT-TYPE
    SYNTAX      DisplayString
    MAX-ACCESS  read-write
    STATUS      current
    DESCRIPTION
	"The second output Min. current alarm value of slave1"
    ::= { slave1OutputCurrentMin 9}

slave1OutputCurrentMinTen OBJECT-TYPE
    SYNTAX      DisplayString
    MAX-ACCESS  read-write
    STATUS      current
    DESCRIPTION
	"The second output Min. current alarm value of slave1"
    ::= { slave1OutputCurrentMin 10}

slave1OutputCurrentMinEleven OBJECT-TYPE
    SYNTAX      DisplayString
    MAX-ACCESS  read-write
    STATUS      current
    DESCRIPTION
	"The second output Min. current alarm value of slave1"
    ::= { slave1OutputCurrentMin 11}

slave1OutputCurrentMinTwel OBJECT-TYPE
    SYNTAX      DisplayString
    MAX-ACCESS  read-write
    STATUS      current
    DESCRIPTION
	"The second output Min. current alarm value of slave1"
    ::= { slave1OutputCurrentMin 12}

slave1OutputCurrentMinThirteen OBJECT-TYPE
    SYNTAX      DisplayString
    MAX-ACCESS  read-write
    STATUS      current
    DESCRIPTION
	"The second output Min. current alarm value of slave1"
    ::= { slave1OutputCurrentMin 13}

slave1OutputCurrentMinFourteen OBJECT-TYPE
    SYNTAX      DisplayString
    MAX-ACCESS  read-write
    STATUS      current
    DESCRIPTION
	"The second output Min. current alarm value of slave1"
    ::= { slave1OutputCurrentMin 14}

slave1OutputCurrentMinFifteen OBJECT-TYPE
    SYNTAX      DisplayString
    MAX-ACCESS  read-write
    STATUS      current
    DESCRIPTION
	"The second output Min. current alarm value of slave1"
    ::= { slave1OutputCurrentMin 15}

slave1OutputCurrentMinSixteen OBJECT-TYPE
    SYNTAX      DisplayString
    MAX-ACCESS  read-write
    STATUS      current
    DESCRIPTION
	"The second output Min. current alarm value of slave1"
    ::= { slave1OutputCurrentMin 16}

slave1OutputCurrentMinSeventeen OBJECT-TYPE
    SYNTAX      DisplayString
    MAX-ACCESS  read-write
    STATUS      current
    DESCRIPTION
	"The second output Min. current alarm value of slave1"
    ::= { slave1OutputCurrentMin 17}

slave1OutputCurrentMinEighteen OBJECT-TYPE
    SYNTAX      DisplayString
    MAX-ACCESS  read-write
    STATUS      current
    DESCRIPTION
	"The second output Min. current alarm value of slave1"
    ::= { slave1OutputCurrentMin 18}
	
slave1OutputCurrentMinNineteen OBJECT-TYPE
    SYNTAX      DisplayString
    MAX-ACCESS  read-write
    STATUS      current
    DESCRIPTION
	"The second output Min. current alarm value of slave1"
    ::= { slave1OutputCurrentMin 19}
	
slave1OutputCurrentMintwenty OBJECT-TYPE
    SYNTAX      DisplayString
    MAX-ACCESS  read-write
    STATUS      current
    DESCRIPTION
	"The second output Min. current alarm value of slave1"
    ::= { slave1OutputCurrentMin 20}
	
slave1OutputCurrentMinTwentyone OBJECT-TYPE
    SYNTAX      DisplayString
    MAX-ACCESS  read-write
    STATUS      current
    DESCRIPTION
	"The second output Min. current alarm value of slave1"
    ::= { slave1OutputCurrentMin 21}
	
slave1OutputCurrentMinTwentyonetwo OBJECT-TYPE
    SYNTAX      DisplayString
    MAX-ACCESS  read-write
    STATUS      current
    DESCRIPTION
	"The second output Min. current alarm value of slave1"
    ::= { slave1OutputCurrentMin 22}
	
slave1OutputCurrentMinTwentythree OBJECT-TYPE
    SYNTAX      DisplayString
    MAX-ACCESS  read-write
    STATUS      current
    DESCRIPTION
	"The second output Min. current alarm value of slave1"
    ::= { slave1OutputCurrentMin 23}
	
slave1OutputCurrentMinTwentyfour OBJECT-TYPE
    SYNTAX      DisplayString
    MAX-ACCESS  read-write
    STATUS      current
    DESCRIPTION
	"The second output Min. current alarm value of slave1"
    ::= { slave1OutputCurrentMin 24}
	
slave1OutputCurrentMinTwentyfive OBJECT-TYPE
    SYNTAX      DisplayString
    MAX-ACCESS  read-write
    STATUS      current
    DESCRIPTION
	"The second output Min. current alarm value of slave1"
    ::= { slave1OutputCurrentMin 25}
	
slave1OutputCurrentMinTwentysix OBJECT-TYPE
    SYNTAX      DisplayString
    MAX-ACCESS  read-write
    STATUS      current
    DESCRIPTION
	"The second output Min. current alarm value of slave1"
    ::= { slave1OutputCurrentMin 26}
	
slave1OutputCurrentMinTwentyseven OBJECT-TYPE
    SYNTAX      DisplayString
    MAX-ACCESS  read-write
    STATUS      current
    DESCRIPTION
	"The second output Min. current alarm value of slave1"
    ::= { slave1OutputCurrentMin 27}
	
slave1OutputCurrentMinTwentyeight OBJECT-TYPE
    SYNTAX      DisplayString
    MAX-ACCESS  read-write
    STATUS      current
    DESCRIPTION
	"The second output Min. current alarm value of slave1"
    ::= { slave1OutputCurrentMin 28}	
slave1OutputCurrentMinTwentynine OBJECT-TYPE
    SYNTAX      DisplayString
    MAX-ACCESS  read-write
    STATUS      current
    DESCRIPTION
	"The second output Min. current alarm value of slave1"
    ::= { slave1OutputCurrentMin 29}
	
slave1OutputCurrentMinThirty OBJECT-TYPE
    SYNTAX      DisplayString
    MAX-ACCESS  read-write
    STATUS      current
    DESCRIPTION
	"The second output Min. current alarm value of slave1"
    ::= { slave1OutputCurrentMin 30}
	
slave1OutputCurrentMinThirtyone OBJECT-TYPE
    SYNTAX      DisplayString
    MAX-ACCESS  read-write
    STATUS      current
    DESCRIPTION
	"The second output Min. current alarm value of slave1"
    ::= { slave1OutputCurrentMin 31}
	
slave1OutputCurrentMinThirtytwo OBJECT-TYPE
    SYNTAX      DisplayString
    MAX-ACCESS  read-write
    STATUS      current
    DESCRIPTION
	"The second output Min. current alarm value of slave1"
    ::= { slave1OutputCurrentMin 32}
	
slave1OutputCurrentMinThirtythree OBJECT-TYPE
    SYNTAX      DisplayString
    MAX-ACCESS  read-write
    STATUS      current
    DESCRIPTION
	"The second output Min. current alarm value of slave1"
    ::= { slave1OutputCurrentMin 33}
	
slave1OutputCurrentMinThirtyfour OBJECT-TYPE
    SYNTAX      DisplayString
    MAX-ACCESS  read-write
    STATUS      current
    DESCRIPTION
	"The second output Min. current alarm value of slave1"
    ::= { slave1OutputCurrentMin 34}
	
slave1OutputCurrentMinThirtyfive OBJECT-TYPE
    SYNTAX      DisplayString
    MAX-ACCESS  read-write
    STATUS      current
    DESCRIPTION
	"The second output Min. current alarm value of slave1"
    ::= { slave1OutputCurrentMin 35}
	
slave1OutputCurrentMinThirtysix OBJECT-TYPE
    SYNTAX      DisplayString
    MAX-ACCESS  read-write
    STATUS      current
    DESCRIPTION
	"The second output Min. current alarm value of slave1"
    ::= { slave1OutputCurrentMin 36}
	
slave1OutputCurrentMinThirtyseven OBJECT-TYPE
    SYNTAX      DisplayString
    MAX-ACCESS  read-write
    STATUS      current
    DESCRIPTION
	"The second output Min. current alarm value of slave1"
    ::= { slave1OutputCurrentMin 37}
	
slave1OutputCurrentMinThirtyeight OBJECT-TYPE
    SYNTAX      DisplayString
    MAX-ACCESS  read-write
    STATUS      current
    DESCRIPTION
	"The second output Min. current alarm value of slave1"
    ::= { slave1OutputCurrentMin 38}
	
slave1OutputCurrentMinThirtynine OBJECT-TYPE
    SYNTAX      DisplayString
    MAX-ACCESS  read-write
    STATUS      current
    DESCRIPTION
	"The second output Min. current alarm value of slave1"
    ::= { slave1OutputCurrentMin 39}
	
slave1OutputCurrentMinFourty OBJECT-TYPE
    SYNTAX      DisplayString
    MAX-ACCESS  read-write
    STATUS      current
    DESCRIPTION
	"The second output Min. current alarm value of slave1"
    ::= { slave1OutputCurrentMin 40}
	
slave1OutputCurrentMinFourtyone OBJECT-TYPE
    SYNTAX      DisplayString
    MAX-ACCESS  read-write
    STATUS      current
    DESCRIPTION
	"The second output Min. current alarm value of slave1"
    ::= { slave1OutputCurrentMin 41}
	
slave1OutputCurrentMinFourtytwo OBJECT-TYPE
    SYNTAX      DisplayString
    MAX-ACCESS  read-write
    STATUS      current
    DESCRIPTION
	"The second output Min. current alarm value of slave1"
    ::= { slave1OutputCurrentMin 42}


------------------------slave1 output current Min critical----------------			
slave1OutputCurrentMinCritical OBJECT IDENTIFIER ::= { slave1OutputCurrent 3}	

slave1OutputCurrentMinCriticalOne OBJECT-TYPE
    SYNTAX      DisplayString
    MAX-ACCESS  read-write
    STATUS      current
    DESCRIPTION
	"The first output Min. current warning value of slave1"
    ::= { slave1OutputCurrentMinCritical 1}

slave1OutputCurrentMinCriticalTwo OBJECT-TYPE
    SYNTAX      DisplayString
    MAX-ACCESS  read-write
    STATUS      current
    DESCRIPTION
	"The second output Min. current warning value of slave1"
    ::= { slave1OutputCurrentMinCritical 2}

slave1OutputCurrentMinCriticalThree OBJECT-TYPE
    SYNTAX      DisplayString
    MAX-ACCESS  read-write
    STATUS      current
    DESCRIPTION
	"The second output Min. current warning value of slave1"
    ::= { slave1OutputCurrentMinCritical 3}

slave1OutputCurrentMinCriticalFour OBJECT-TYPE
    SYNTAX      DisplayString
    MAX-ACCESS  read-write
    STATUS      current
    DESCRIPTION
	"The second output Min. current warning value of slave1"
    ::= { slave1OutputCurrentMinCritical 4}

slave1OutputCurrentMinCriticalFive OBJECT-TYPE
    SYNTAX      DisplayString
    MAX-ACCESS  read-write
    STATUS      current
    DESCRIPTION
	"The second output Min. current warning value of slave1"
    ::= { slave1OutputCurrentMinCritical 5}

slave1OutputCurrentMinCriticalSix OBJECT-TYPE
    SYNTAX      DisplayString
    MAX-ACCESS  read-write
    STATUS      current
    DESCRIPTION
	"The second output Min. current warning value of slave1"
    ::= { slave1OutputCurrentMinCritical 6}

slave1OutputCurrentMinCriticalSeven OBJECT-TYPE
    SYNTAX      DisplayString
    MAX-ACCESS  read-write
    STATUS      current
    DESCRIPTION
	"The second output Min. current warning value of slave1"
    ::= { slave1OutputCurrentMinCritical 7}

slave1OutputCurrentMinCriticalEight OBJECT-TYPE
    SYNTAX      DisplayString
    MAX-ACCESS  read-write
    STATUS      current
    DESCRIPTION
	"The second output Min. current warning value of slave1"
    ::= { slave1OutputCurrentMinCritical 8}

slave1OutputCurrentMinCriticalNine OBJECT-TYPE
    SYNTAX      DisplayString
    MAX-ACCESS  read-write
    STATUS      current
    DESCRIPTION
	"The second output Min. current warning value of slave1"
    ::= { slave1OutputCurrentMinCritical 9}

slave1OutputCurrentMinCriticalTen OBJECT-TYPE
    SYNTAX      DisplayString
    MAX-ACCESS  read-write
    STATUS      current
    DESCRIPTION
	"The second output Min. current warning value of slave1"
    ::= { slave1OutputCurrentMinCritical 10}

slave1OutputCurrentMinCriticalEleven OBJECT-TYPE
    SYNTAX      DisplayString
    MAX-ACCESS  read-write
    STATUS      current
    DESCRIPTION
	"The second output Min. current warning value of slave1"
    ::= { slave1OutputCurrentMinCritical 11}

slave1OutputCurrentMinCriticalTwel OBJECT-TYPE
    SYNTAX      DisplayString
    MAX-ACCESS  read-write
    STATUS      current
    DESCRIPTION
	"The second output Min. current warning value of slave1"
    ::= { slave1OutputCurrentMinCritical 12}

slave1OutputCurrentMinCriticalThirteen OBJECT-TYPE
    SYNTAX      DisplayString
    MAX-ACCESS  read-write
    STATUS      current
    DESCRIPTION
	"The second output Min. current warning value of slave1"
    ::= { slave1OutputCurrentMinCritical 13}

slave1OutputCurrentMinCriticalFourteen OBJECT-TYPE
    SYNTAX      DisplayString
    MAX-ACCESS  read-write
    STATUS      current
    DESCRIPTION
	"The second output Min. current warning value of slave1"
    ::= { slave1OutputCurrentMinCritical 14}

slave1OutputCurrentMinCriticalFifteen OBJECT-TYPE
    SYNTAX      DisplayString
    MAX-ACCESS  read-write
    STATUS      current
    DESCRIPTION
	"The second output Min. current warning value of slave1"
    ::= { slave1OutputCurrentMinCritical 15}

slave1OutputCurrentMinCriticalSixteen OBJECT-TYPE
    SYNTAX      DisplayString
    MAX-ACCESS  read-write
    STATUS      current
    DESCRIPTION
	"The second output Min. current warning value of slave1"
    ::= { slave1OutputCurrentMinCritical 16}

slave1OutputCurrentMinCriticalSeventeen OBJECT-TYPE
    SYNTAX      DisplayString
    MAX-ACCESS  read-write
    STATUS      current
    DESCRIPTION
	"The second output Min. current warning value of slave1"
    ::= { slave1OutputCurrentMinCritical 17}

slave1OutputCurrentMinCriticalEighteen OBJECT-TYPE
    SYNTAX      DisplayString
    MAX-ACCESS  read-write
    STATUS      current
    DESCRIPTION
	"The second output Min. current warning value of slave1"
    ::= { slave1OutputCurrentMinCritical 18}
	
slave1OutputCurrentMinCriticalNineteen OBJECT-TYPE
    SYNTAX      DisplayString
    MAX-ACCESS  read-write
    STATUS      current
    DESCRIPTION
	"The second output Min. current warning value of slave1"
    ::= { slave1OutputCurrentMinCritical 19}
	
slave1OutputCurrentMinCriticaltwenty OBJECT-TYPE
    SYNTAX      DisplayString
    MAX-ACCESS  read-write
    STATUS      current
    DESCRIPTION
	"The second output Min. current warning value of slave1"
    ::= { slave1OutputCurrentMinCritical 20}
	
slave1OutputCurrentMinCriticalTwentyone OBJECT-TYPE
    SYNTAX      DisplayString
    MAX-ACCESS  read-write
    STATUS      current
    DESCRIPTION
	"The second output Min. current warning value of slave1"
    ::= { slave1OutputCurrentMinCritical 21}
	
slave1OutputCurrentMinCriticalTwentyonetwo OBJECT-TYPE
    SYNTAX      DisplayString
    MAX-ACCESS  read-write
    STATUS      current
    DESCRIPTION
	"The second output Min. current warning value of slave1"
    ::= { slave1OutputCurrentMinCritical 22}
	
slave1OutputCurrentMinCriticalTwentythree OBJECT-TYPE
    SYNTAX      DisplayString
    MAX-ACCESS  read-write
    STATUS      current
    DESCRIPTION
	"The second output Min. current warning value of slave1"
    ::= { slave1OutputCurrentMinCritical 23}
	
slave1OutputCurrentMinCriticalTwentyfour OBJECT-TYPE
    SYNTAX      DisplayString
    MAX-ACCESS  read-write
    STATUS      current
    DESCRIPTION
	"The second output Min. current warning value of slave1"
    ::= { slave1OutputCurrentMinCritical 24}
	
slave1OutputCurrentMinCriticalTwentyfive OBJECT-TYPE
    SYNTAX      DisplayString
    MAX-ACCESS  read-write
    STATUS      current
    DESCRIPTION
	"The second output Min. current warning value of slave1"
    ::= { slave1OutputCurrentMinCritical 25}
	
slave1OutputCurrentMinCriticalTwentysix OBJECT-TYPE
    SYNTAX      DisplayString
    MAX-ACCESS  read-write
    STATUS      current
    DESCRIPTION
	"The second output Min. current warning value of slave1"
    ::= { slave1OutputCurrentMinCritical 26}
	
slave1OutputCurrentMinCriticalTwentyseven OBJECT-TYPE
    SYNTAX      DisplayString
    MAX-ACCESS  read-write
    STATUS      current
    DESCRIPTION
	"The second output Min. current warning value of slave1"
    ::= { slave1OutputCurrentMinCritical 27}
	
slave1OutputCurrentMinCriticalTwentyeight OBJECT-TYPE
    SYNTAX      DisplayString
    MAX-ACCESS  read-write
    STATUS      current
    DESCRIPTION
	"The second output Min. current warning value of slave1"
    ::= { slave1OutputCurrentMinCritical 28}	
slave1OutputCurrentMinCriticalTwentynine OBJECT-TYPE
    SYNTAX      DisplayString
    MAX-ACCESS  read-write
    STATUS      current
    DESCRIPTION
	"The second output Min. current warning value of slave1"
    ::= { slave1OutputCurrentMinCritical 29}
	
slave1OutputCurrentMinCriticalThirty OBJECT-TYPE
    SYNTAX      DisplayString
    MAX-ACCESS  read-write
    STATUS      current
    DESCRIPTION
	"The second output Min. current warning value of slave1"
    ::= { slave1OutputCurrentMinCritical 30}
	
slave1OutputCurrentMinCriticalThirtyone OBJECT-TYPE
    SYNTAX      DisplayString
    MAX-ACCESS  read-write
    STATUS      current
    DESCRIPTION
	"The second output Min. current warning value of slave1"
    ::= { slave1OutputCurrentMinCritical 31}
	
slave1OutputCurrentMinCriticalThirtytwo OBJECT-TYPE
    SYNTAX      DisplayString
    MAX-ACCESS  read-write
    STATUS      current
    DESCRIPTION
	"The second output Min. current warning value of slave1"
    ::= { slave1OutputCurrentMinCritical 32}
	
slave1OutputCurrentMinCriticalThirtythree OBJECT-TYPE
    SYNTAX      DisplayString
    MAX-ACCESS  read-write
    STATUS      current
    DESCRIPTION
	"The second output Min. current warning value of slave1"
    ::= { slave1OutputCurrentMinCritical 33}
	
slave1OutputCurrentMinCriticalThirtyfour OBJECT-TYPE
    SYNTAX      DisplayString
    MAX-ACCESS  read-write
    STATUS      current
    DESCRIPTION
	"The second output Min. current warning value of slave1"
    ::= { slave1OutputCurrentMinCritical 34}
	
slave1OutputCurrentMinCriticalThirtyfive OBJECT-TYPE
    SYNTAX      DisplayString
    MAX-ACCESS  read-write
    STATUS      current
    DESCRIPTION
	"The second output Min. current warning value of slave1"
    ::= { slave1OutputCurrentMinCritical 35}
	
slave1OutputCurrentMinCriticalThirtysix OBJECT-TYPE
    SYNTAX      DisplayString
    MAX-ACCESS  read-write
    STATUS      current
    DESCRIPTION
	"The second output Min. current warning value of slave1"
    ::= { slave1OutputCurrentMinCritical 36}
	
slave1OutputCurrentMinCriticalThirtyseven OBJECT-TYPE
    SYNTAX      DisplayString
    MAX-ACCESS  read-write
    STATUS      current
    DESCRIPTION
	"The second output Min. current warning value of slave1"
    ::= { slave1OutputCurrentMinCritical 37}
	
slave1OutputCurrentMinCriticalThirtyeight OBJECT-TYPE
    SYNTAX      DisplayString
    MAX-ACCESS  read-write
    STATUS      current
    DESCRIPTION
	"The second output Min. current warning value of slave1"
    ::= { slave1OutputCurrentMinCritical 38}
	
slave1OutputCurrentMinCriticalThirtynine OBJECT-TYPE
    SYNTAX      DisplayString
    MAX-ACCESS  read-write
    STATUS      current
    DESCRIPTION
	"The second output Min. current warning value of slave1"
    ::= { slave1OutputCurrentMinCritical 39}
	
slave1OutputCurrentMinCriticalFourty OBJECT-TYPE
    SYNTAX      DisplayString
    MAX-ACCESS  read-write
    STATUS      current
    DESCRIPTION
	"The second output Min. current warning value of slave1"
    ::= { slave1OutputCurrentMinCritical 40}
	
slave1OutputCurrentMinCriticalFourtyone OBJECT-TYPE
    SYNTAX      DisplayString
    MAX-ACCESS  read-write
    STATUS      current
    DESCRIPTION
	"The second output Min. current warning value of slave1"
    ::= { slave1OutputCurrentMinCritical 41}
	
slave1OutputCurrentMinCriticalFourtytwo OBJECT-TYPE
    SYNTAX      DisplayString
    MAX-ACCESS  read-write
    STATUS      current
    DESCRIPTION
	"The second output Min. current warning value of slave1"
    ::= { slave1OutputCurrentMinCritical 42}
	
	
------------------------slave1 output current Max critical----------------			
slave1OutputCurrentMaxCritical OBJECT IDENTIFIER ::= { slave1OutputCurrent 4}	

slave1OutputCurrentMaxCriticalOne OBJECT-TYPE
    SYNTAX      DisplayString
    MAX-ACCESS  read-write
    STATUS      current
    DESCRIPTION
	"The first output Max. current warning value of slave1"
    ::= { slave1OutputCurrentMaxCritical 1}

slave1OutputCurrentMaxCriticalTwo OBJECT-TYPE
    SYNTAX      DisplayString
    MAX-ACCESS  read-write
    STATUS      current
    DESCRIPTION
	"The second output Max. current warning value of slave1"
    ::= { slave1OutputCurrentMaxCritical 2}

slave1OutputCurrentMaxCriticalThree OBJECT-TYPE
    SYNTAX      DisplayString
    MAX-ACCESS  read-write
    STATUS      current
    DESCRIPTION
	"The second output Max. current warning value of slave1"
    ::= { slave1OutputCurrentMaxCritical 3}

slave1OutputCurrentMaxCriticalFour OBJECT-TYPE
    SYNTAX      DisplayString
    MAX-ACCESS  read-write
    STATUS      current
    DESCRIPTION
	"The second output Max. current warning value of slave1"
    ::= { slave1OutputCurrentMaxCritical 4}

slave1OutputCurrentMaxCriticalFive OBJECT-TYPE
    SYNTAX      DisplayString
    MAX-ACCESS  read-write
    STATUS      current
    DESCRIPTION
	"The second output Max. current warning value of slave1"
    ::= { slave1OutputCurrentMaxCritical 5}

slave1OutputCurrentMaxCriticalSix OBJECT-TYPE
    SYNTAX      DisplayString
    MAX-ACCESS  read-write
    STATUS      current
    DESCRIPTION
	"The second output Max. current warning value of slave1"
    ::= { slave1OutputCurrentMaxCritical 6}

slave1OutputCurrentMaxCriticalSeven OBJECT-TYPE
    SYNTAX      DisplayString
    MAX-ACCESS  read-write
    STATUS      current
    DESCRIPTION
	"The second output Max. current warning value of slave1"
    ::= { slave1OutputCurrentMaxCritical 7}

slave1OutputCurrentMaxCriticalEight OBJECT-TYPE
    SYNTAX      DisplayString
    MAX-ACCESS  read-write
    STATUS      current
    DESCRIPTION
	"The second output Max. current warning value of slave1"
    ::= { slave1OutputCurrentMaxCritical 8}

slave1OutputCurrentMaxCriticalNine OBJECT-TYPE
    SYNTAX      DisplayString
    MAX-ACCESS  read-write
    STATUS      current
    DESCRIPTION
	"The second output Max. current warning value of slave1"
    ::= { slave1OutputCurrentMaxCritical 9}

slave1OutputCurrentMaxCriticalTen OBJECT-TYPE
    SYNTAX      DisplayString
    MAX-ACCESS  read-write
    STATUS      current
    DESCRIPTION
	"The second output Max. current warning value of slave1"
    ::= { slave1OutputCurrentMaxCritical 10}

slave1OutputCurrentMaxCriticalEleven OBJECT-TYPE
    SYNTAX      DisplayString
    MAX-ACCESS  read-write
    STATUS      current
    DESCRIPTION
	"The second output Max. current warning value of slave1"
    ::= { slave1OutputCurrentMaxCritical 11}

slave1OutputCurrentMaxCriticalTwel OBJECT-TYPE
    SYNTAX      DisplayString
    MAX-ACCESS  read-write
    STATUS      current
    DESCRIPTION
	"The second output Max. current warning value of slave1"
    ::= { slave1OutputCurrentMaxCritical 12}

slave1OutputCurrentMaxCriticalThirteen OBJECT-TYPE
    SYNTAX      DisplayString
    MAX-ACCESS  read-write
    STATUS      current
    DESCRIPTION
	"The second output Max. current warning value of slave1"
    ::= { slave1OutputCurrentMaxCritical 13}

slave1OutputCurrentMaxCriticalFourteen OBJECT-TYPE
    SYNTAX      DisplayString
    MAX-ACCESS  read-write
    STATUS      current
    DESCRIPTION
	"The second output Max. current warning value of slave1"
    ::= { slave1OutputCurrentMaxCritical 14}

slave1OutputCurrentMaxCriticalFifteen OBJECT-TYPE
    SYNTAX      DisplayString
    MAX-ACCESS  read-write
    STATUS      current
    DESCRIPTION
	"The second output Max. current warning value of slave1"
    ::= { slave1OutputCurrentMaxCritical 15}

slave1OutputCurrentMaxCriticalSixteen OBJECT-TYPE
    SYNTAX      DisplayString
    MAX-ACCESS  read-write
    STATUS      current
    DESCRIPTION
	"The second output Max. current warning value of slave1"
    ::= { slave1OutputCurrentMaxCritical 16}

slave1OutputCurrentMaxCriticalSeventeen OBJECT-TYPE
    SYNTAX      DisplayString
    MAX-ACCESS  read-write
    STATUS      current
    DESCRIPTION
	"The second output Max. current warning value of slave1"
    ::= { slave1OutputCurrentMaxCritical 17}

slave1OutputCurrentMaxCriticalEighteen OBJECT-TYPE
    SYNTAX      DisplayString
    MAX-ACCESS  read-write
    STATUS      current
    DESCRIPTION
	"The second output Max. current warning value of slave1"
    ::= { slave1OutputCurrentMaxCritical 18}
	
slave1OutputCurrentMaxCriticalNineteen OBJECT-TYPE
    SYNTAX      DisplayString
    MAX-ACCESS  read-write
    STATUS      current
    DESCRIPTION
	"The second output Max. current warning value of slave1"
    ::= { slave1OutputCurrentMaxCritical 19}
	
slave1OutputCurrentMaxCriticaltwenty OBJECT-TYPE
    SYNTAX      DisplayString
    MAX-ACCESS  read-write
    STATUS      current
    DESCRIPTION
	"The second output Max. current warning value of slave1"
    ::= { slave1OutputCurrentMaxCritical 20}
	
slave1OutputCurrentMaxCriticalTwentyone OBJECT-TYPE
    SYNTAX      DisplayString
    MAX-ACCESS  read-write
    STATUS      current
    DESCRIPTION
	"The second output Max. current warning value of slave1"
    ::= { slave1OutputCurrentMaxCritical 21}
	
slave1OutputCurrentMaxCriticalTwentyonetwo OBJECT-TYPE
    SYNTAX      DisplayString
    MAX-ACCESS  read-write
    STATUS      current
    DESCRIPTION
	"The second output Max. current warning value of slave1"
    ::= { slave1OutputCurrentMaxCritical 22}
	
slave1OutputCurrentMaxCriticalTwentythree OBJECT-TYPE
    SYNTAX      DisplayString
    MAX-ACCESS  read-write
    STATUS      current
    DESCRIPTION
	"The second output Max. current warning value of slave1"
    ::= { slave1OutputCurrentMaxCritical 23}
	
slave1OutputCurrentMaxCriticalTwentyfour OBJECT-TYPE
    SYNTAX      DisplayString
    MAX-ACCESS  read-write
    STATUS      current
    DESCRIPTION
	"The second output Max. current warning value of slave1"
    ::= { slave1OutputCurrentMaxCritical 24}
	
slave1OutputCurrentMaxCriticalTwentyfive OBJECT-TYPE
    SYNTAX      DisplayString
    MAX-ACCESS  read-write
    STATUS      current
    DESCRIPTION
	"The second output Max. current warning value of slave1"
    ::= { slave1OutputCurrentMaxCritical 25}
	
slave1OutputCurrentMaxCriticalTwentysix OBJECT-TYPE
    SYNTAX      DisplayString
    MAX-ACCESS  read-write
    STATUS      current
    DESCRIPTION
	"The second output Max. current warning value of slave1"
    ::= { slave1OutputCurrentMaxCritical 26}
	
slave1OutputCurrentMaxCriticalTwentyseven OBJECT-TYPE
    SYNTAX      DisplayString
    MAX-ACCESS  read-write
    STATUS      current
    DESCRIPTION
	"The second output Max. current warning value of slave1"
    ::= { slave1OutputCurrentMaxCritical 27}
	
slave1OutputCurrentMaxCriticalTwentyeight OBJECT-TYPE
    SYNTAX      DisplayString
    MAX-ACCESS  read-write
    STATUS      current
    DESCRIPTION
	"The second output Max. current warning value of slave1"
    ::= { slave1OutputCurrentMaxCritical 28}	
slave1OutputCurrentMaxCriticalTwentynine OBJECT-TYPE
    SYNTAX      DisplayString
    MAX-ACCESS  read-write
    STATUS      current
    DESCRIPTION
	"The second output Max. current warning value of slave1"
    ::= { slave1OutputCurrentMaxCritical 29}
	
slave1OutputCurrentMaxCriticalThirty OBJECT-TYPE
    SYNTAX      DisplayString
    MAX-ACCESS  read-write
    STATUS      current
    DESCRIPTION
	"The second output Max. current warning value of slave1"
    ::= { slave1OutputCurrentMaxCritical 30}
	
slave1OutputCurrentMaxCriticalThirtyone OBJECT-TYPE
    SYNTAX      DisplayString
    MAX-ACCESS  read-write
    STATUS      current
    DESCRIPTION
	"The second output Max. current warning value of slave1"
    ::= { slave1OutputCurrentMaxCritical 31}
	
slave1OutputCurrentMaxCriticalThirtytwo OBJECT-TYPE
    SYNTAX      DisplayString
    MAX-ACCESS  read-write
    STATUS      current
    DESCRIPTION
	"The second output Max. current warning value of slave1"
    ::= { slave1OutputCurrentMaxCritical 32}
	
slave1OutputCurrentMaxCriticalThirtythree OBJECT-TYPE
    SYNTAX      DisplayString
    MAX-ACCESS  read-write
    STATUS      current
    DESCRIPTION
	"The second output Max. current warning value of slave1"
    ::= { slave1OutputCurrentMaxCritical 33}
	
slave1OutputCurrentMaxCriticalThirtyfour OBJECT-TYPE
    SYNTAX      DisplayString
    MAX-ACCESS  read-write
    STATUS      current
    DESCRIPTION
	"The second output Max. current warning value of slave1"
    ::= { slave1OutputCurrentMaxCritical 34}
	
slave1OutputCurrentMaxCriticalThirtyfive OBJECT-TYPE
    SYNTAX      DisplayString
    MAX-ACCESS  read-write
    STATUS      current
    DESCRIPTION
	"The second output Max. current warning value of slave1"
    ::= { slave1OutputCurrentMaxCritical 35}
	
slave1OutputCurrentMaxCriticalThirtysix OBJECT-TYPE
    SYNTAX      DisplayString
    MAX-ACCESS  read-write
    STATUS      current
    DESCRIPTION
	"The second output Max. current warning value of slave1"
    ::= { slave1OutputCurrentMaxCritical 36}
	
slave1OutputCurrentMaxCriticalThirtyseven OBJECT-TYPE
    SYNTAX      DisplayString
    MAX-ACCESS  read-write
    STATUS      current
    DESCRIPTION
	"The second output Max. current warning value of slave1"
    ::= { slave1OutputCurrentMaxCritical 37}
	
slave1OutputCurrentMaxCriticalThirtyeight OBJECT-TYPE
    SYNTAX      DisplayString
    MAX-ACCESS  read-write
    STATUS      current
    DESCRIPTION
	"The second output Max. current warning value of slave1"
    ::= { slave1OutputCurrentMaxCritical 38}
	
slave1OutputCurrentMaxCriticalThirtynine OBJECT-TYPE
    SYNTAX      DisplayString
    MAX-ACCESS  read-write
    STATUS      current
    DESCRIPTION
	"The second output Max. current warning value of slave1"
    ::= { slave1OutputCurrentMaxCritical 39}
	
slave1OutputCurrentMaxCriticalFourty OBJECT-TYPE
    SYNTAX      DisplayString
    MAX-ACCESS  read-write
    STATUS      current
    DESCRIPTION
	"The second output Max. current warning value of slave1"
    ::= { slave1OutputCurrentMaxCritical 40}
	
slave1OutputCurrentMaxCriticalFourtyone OBJECT-TYPE
    SYNTAX      DisplayString
    MAX-ACCESS  read-write
    STATUS      current
    DESCRIPTION
	"The second output Max. current warning value of slave1"
    ::= { slave1OutputCurrentMaxCritical 41}
	
slave1OutputCurrentMaxCriticalFourtytwo OBJECT-TYPE
    SYNTAX      DisplayString
    MAX-ACCESS  read-write
    STATUS      current
    DESCRIPTION
	"The second output Max. current warning value of slave1"
    ::= { slave1OutputCurrentMaxCritical 42}
	
	
------------------------slave1 output current Max----------------			
slave1OutputCurrentMax OBJECT IDENTIFIER ::= { slave1OutputCurrent 5}
	
slave1OutputCurrentMaxOne OBJECT-TYPE
    SYNTAX      DisplayString
    MAX-ACCESS  read-write
    STATUS      current
    DESCRIPTION
	"The first output Max. current alarm value of slave1"
    ::= { slave1OutputCurrentMax 1}

slave1OutputCurrentMaxTwo OBJECT-TYPE
    SYNTAX      DisplayString
    MAX-ACCESS  read-write
    STATUS      current
    DESCRIPTION
	"The second output Max. current alarm value of slave1"
    ::= { slave1OutputCurrentMax 2}

slave1OutputCurrentMaxThree OBJECT-TYPE
    SYNTAX      DisplayString
    MAX-ACCESS  read-write
    STATUS      current
    DESCRIPTION
	"The second output Max. current alarm value of slave1"
    ::= { slave1OutputCurrentMax 3}

slave1OutputCurrentMaxFour OBJECT-TYPE
    SYNTAX      DisplayString
    MAX-ACCESS  read-write
    STATUS      current
    DESCRIPTION
	"The second output Max. current alarm value of slave1"
    ::= { slave1OutputCurrentMax 4}

slave1OutputCurrentMaxFive OBJECT-TYPE
    SYNTAX      DisplayString
    MAX-ACCESS  read-write
    STATUS      current
    DESCRIPTION
	"The second output Max. current alarm value of slave1"
    ::= { slave1OutputCurrentMax 5}

slave1OutputCurrentMaxSix OBJECT-TYPE
    SYNTAX      DisplayString
    MAX-ACCESS  read-write
    STATUS      current
    DESCRIPTION
	"The second output Max. current alarm value of slave1"
    ::= { slave1OutputCurrentMax 6}

slave1OutputCurrentMaxSeven OBJECT-TYPE
    SYNTAX      DisplayString
    MAX-ACCESS  read-write
    STATUS      current
    DESCRIPTION
	"The second output Max. current alarm value of slave1"
    ::= { slave1OutputCurrentMax 7}

slave1OutputCurrentMaxEight OBJECT-TYPE
    SYNTAX      DisplayString
    MAX-ACCESS  read-write
    STATUS      current
    DESCRIPTION
	"The second output Max. current alarm value of slave1"
    ::= { slave1OutputCurrentMax 8}

slave1OutputCurrentMaxNine OBJECT-TYPE
    SYNTAX      DisplayString
    MAX-ACCESS  read-write
    STATUS      current
    DESCRIPTION
	"The second output Max. current alarm value of slave1"
    ::= { slave1OutputCurrentMax 9}

slave1OutputCurrentMaxTen OBJECT-TYPE
    SYNTAX      DisplayString
    MAX-ACCESS  read-write
    STATUS      current
    DESCRIPTION
	"The second output Max. current alarm value of slave1"
    ::= { slave1OutputCurrentMax 10}

slave1OutputCurrentMaxEleven OBJECT-TYPE
    SYNTAX      DisplayString
    MAX-ACCESS  read-write
    STATUS      current
    DESCRIPTION
	"The second output Max. current alarm value of slave1"
    ::= { slave1OutputCurrentMax 11}

slave1OutputCurrentMaxTwel OBJECT-TYPE
    SYNTAX      DisplayString
    MAX-ACCESS  read-write
    STATUS      current
    DESCRIPTION
	"The second output Max. current alarm value of slave1"
    ::= { slave1OutputCurrentMax 12}

slave1OutputCurrentMaxThirteen OBJECT-TYPE
    SYNTAX      DisplayString
    MAX-ACCESS  read-write
    STATUS      current
    DESCRIPTION
	"The second output Max. current alarm value of slave1"
    ::= { slave1OutputCurrentMax 13}

slave1OutputCurrentMaxFourteen OBJECT-TYPE
    SYNTAX      DisplayString
    MAX-ACCESS  read-write
    STATUS      current
    DESCRIPTION
	"The second output Max. current alarm value of slave1"
    ::= { slave1OutputCurrentMax 14}

slave1OutputCurrentMaxFifteen OBJECT-TYPE
    SYNTAX      DisplayString
    MAX-ACCESS  read-write
    STATUS      current
    DESCRIPTION
	"The second output Max. current alarm value of slave1"
    ::= { slave1OutputCurrentMax 15}

slave1OutputCurrentMaxSixteen OBJECT-TYPE
    SYNTAX      DisplayString
    MAX-ACCESS  read-write
    STATUS      current
    DESCRIPTION
	"The second output Max. current alarm value of slave1"
    ::= { slave1OutputCurrentMax 16}

slave1OutputCurrentMaxSeventeen OBJECT-TYPE
    SYNTAX      DisplayString
    MAX-ACCESS  read-write
    STATUS      current
    DESCRIPTION
	"The second output Max. current alarm value of slave1"
    ::= { slave1OutputCurrentMax 17}

slave1OutputCurrentMaxEighteen OBJECT-TYPE
    SYNTAX      DisplayString
    MAX-ACCESS  read-write
    STATUS      current
    DESCRIPTION
	"The second output Max. current alarm value of slave1"
    ::= { slave1OutputCurrentMax 18}
	
slave1OutputCurrentMaxNineteen OBJECT-TYPE
    SYNTAX      DisplayString
    MAX-ACCESS  read-write
    STATUS      current
    DESCRIPTION
	"The second output Max. current alarm value of slave1"
    ::= { slave1OutputCurrentMax 19}
	
slave1OutputCurrentMaxtwenty OBJECT-TYPE
    SYNTAX      DisplayString
    MAX-ACCESS  read-write
    STATUS      current
    DESCRIPTION
	"The second output Max. current alarm value of slave1"
    ::= { slave1OutputCurrentMax 20}
	
slave1OutputCurrentMaxTwentyone OBJECT-TYPE
    SYNTAX      DisplayString
    MAX-ACCESS  read-write
    STATUS      current
    DESCRIPTION
	"The second output Max. current alarm value of slave1"
    ::= { slave1OutputCurrentMax 21}
	
slave1OutputCurrentMaxTwentyonetwo OBJECT-TYPE
    SYNTAX      DisplayString
    MAX-ACCESS  read-write
    STATUS      current
    DESCRIPTION
	"The second output Max. current alarm value of slave1"
    ::= { slave1OutputCurrentMax 22}
	
slave1OutputCurrentMaxTwentythree OBJECT-TYPE
    SYNTAX      DisplayString
    MAX-ACCESS  read-write
    STATUS      current
    DESCRIPTION
	"The second output Max. current alarm value of slave1"
    ::= { slave1OutputCurrentMax 23}
	
slave1OutputCurrentMaxTwentyfour OBJECT-TYPE
    SYNTAX      DisplayString
    MAX-ACCESS  read-write
    STATUS      current
    DESCRIPTION
	"The second output Max. current alarm value of slave1"
    ::= { slave1OutputCurrentMax 24}
	
slave1OutputCurrentMaxTwentyfive OBJECT-TYPE
    SYNTAX      DisplayString
    MAX-ACCESS  read-write
    STATUS      current
    DESCRIPTION
	"The second output Max. current alarm value of slave1"
    ::= { slave1OutputCurrentMax 25}
	
slave1OutputCurrentMaxTwentysix OBJECT-TYPE
    SYNTAX      DisplayString
    MAX-ACCESS  read-write
    STATUS      current
    DESCRIPTION
	"The second output Max. current alarm value of slave1"
    ::= { slave1OutputCurrentMax 26}
	
slave1OutputCurrentMaxTwentyseven OBJECT-TYPE
    SYNTAX      DisplayString
    MAX-ACCESS  read-write
    STATUS      current
    DESCRIPTION
	"The second output Max. current alarm value of slave1"
    ::= { slave1OutputCurrentMax 27}
	
slave1OutputCurrentMaxTwentyeight OBJECT-TYPE
    SYNTAX      DisplayString
    MAX-ACCESS  read-write
    STATUS      current
    DESCRIPTION
	"The second output Max. current alarm value of slave1"
    ::= { slave1OutputCurrentMax 28}	
slave1OutputCurrentMaxTwentynine OBJECT-TYPE
    SYNTAX      DisplayString
    MAX-ACCESS  read-write
    STATUS      current
    DESCRIPTION
	"The second output Max. current alarm value of slave1"
    ::= { slave1OutputCurrentMax 29}
	
slave1OutputCurrentMaxThirty OBJECT-TYPE
    SYNTAX      DisplayString
    MAX-ACCESS  read-write
    STATUS      current
    DESCRIPTION
	"The second output Max. current alarm value of slave1"
    ::= { slave1OutputCurrentMax 30}
	
slave1OutputCurrentMaxThirtyone OBJECT-TYPE
    SYNTAX      DisplayString
    MAX-ACCESS  read-write
    STATUS      current
    DESCRIPTION
	"The second output Max. current alarm value of slave1"
    ::= { slave1OutputCurrentMax 31}
	
slave1OutputCurrentMaxThirtytwo OBJECT-TYPE
    SYNTAX      DisplayString
    MAX-ACCESS  read-write
    STATUS      current
    DESCRIPTION
	"The second output Max. current alarm value of slave1"
    ::= { slave1OutputCurrentMax 32}
	
slave1OutputCurrentMaxThirtythree OBJECT-TYPE
    SYNTAX      DisplayString
    MAX-ACCESS  read-write
    STATUS      current
    DESCRIPTION
	"The second output Max. current alarm value of slave1"
    ::= { slave1OutputCurrentMax 33}
	
slave1OutputCurrentMaxThirtyfour OBJECT-TYPE
    SYNTAX      DisplayString
    MAX-ACCESS  read-write
    STATUS      current
    DESCRIPTION
	"The second output Max. current alarm value of slave1"
    ::= { slave1OutputCurrentMax 34}
	
slave1OutputCurrentMaxThirtyfive OBJECT-TYPE
    SYNTAX      DisplayString
    MAX-ACCESS  read-write
    STATUS      current
    DESCRIPTION
	"The second output Max. current alarm value of slave1"
    ::= { slave1OutputCurrentMax 35}
	
slave1OutputCurrentMaxThirtysix OBJECT-TYPE
    SYNTAX      DisplayString
    MAX-ACCESS  read-write
    STATUS      current
    DESCRIPTION
	"The second output Max. current alarm value of slave1"
    ::= { slave1OutputCurrentMax 36}
	
slave1OutputCurrentMaxThirtyseven OBJECT-TYPE
    SYNTAX      DisplayString
    MAX-ACCESS  read-write
    STATUS      current
    DESCRIPTION
	"The second output Max. current alarm value of slave1"
    ::= { slave1OutputCurrentMax 37}
	
slave1OutputCurrentMaxThirtyeight OBJECT-TYPE
    SYNTAX      DisplayString
    MAX-ACCESS  read-write
    STATUS      current
    DESCRIPTION
	"The second output Max. current alarm value of slave1"
    ::= { slave1OutputCurrentMax 38}
	
slave1OutputCurrentMaxThirtynine OBJECT-TYPE
    SYNTAX      DisplayString
    MAX-ACCESS  read-write
    STATUS      current
    DESCRIPTION
	"The second output Max. current alarm value of slave1"
    ::= { slave1OutputCurrentMax 39}
	
slave1OutputCurrentMaxFourty OBJECT-TYPE
    SYNTAX      DisplayString
    MAX-ACCESS  read-write
    STATUS      current
    DESCRIPTION
	"The second output Max. current alarm value of slave1"
    ::= { slave1OutputCurrentMax 40}
	
slave1OutputCurrentMaxFourtyone OBJECT-TYPE
    SYNTAX      DisplayString
    MAX-ACCESS  read-write
    STATUS      current
    DESCRIPTION
	"The second output Max. current alarm value of slave1"
    ::= { slave1OutputCurrentMax 41}
	
slave1OutputCurrentMaxFourtytwo OBJECT-TYPE
    SYNTAX      DisplayString
    MAX-ACCESS  read-write
    STATUS      current
    DESCRIPTION
	"The second output Max. current alarm value of slave1"
    ::= { slave1OutputCurrentMax 42}
	
	
-------------------------------slave1 output powerfactor------------------------	
slave1OutputPowerfactor OBJECT IDENTIFIER ::= { slave1 9}	

slave1OutputPowerfactorOne OBJECT-TYPE
    SYNTAX      DisplayString
    MAX-ACCESS  read-only
    STATUS      current
    DESCRIPTION
	"The ouput power factor of slave1." 
	::= { slave1OutputPowerfactor 1}

slave1OutputPowerfactorTwo OBJECT-TYPE
    SYNTAX      DisplayString
    MAX-ACCESS  read-only
    STATUS      current
    DESCRIPTION
	"The ouput power factor of slave1." 
	::= { slave1OutputPowerfactor 2}
	
slave1OutputPowerfactorThree OBJECT-TYPE
    SYNTAX      DisplayString
    MAX-ACCESS  read-only
    STATUS      current
    DESCRIPTION
	"The ouput power factor of slave1." 
	::= { slave1OutputPowerfactor 3}
	
slave1OutputPowerfactorFour OBJECT-TYPE
    SYNTAX      DisplayString
    MAX-ACCESS  read-only
    STATUS      current
    DESCRIPTION
	"The ouput power factor of slave1." 
	::= { slave1OutputPowerfactor 4}
		
slave1OutputPowerfactorFive OBJECT-TYPE
    SYNTAX      DisplayString
    MAX-ACCESS  read-only
    STATUS      current
    DESCRIPTION
	"The ouput power factor of slave1." 
	::= { slave1OutputPowerfactor 5}
	
slave1OutputPowerfactorSix OBJECT-TYPE
    SYNTAX      DisplayString
    MAX-ACCESS  read-only
    STATUS      current
    DESCRIPTION
	"The ouput power factor of slave1." 
	::= { slave1OutputPowerfactor 6}
	
slave1OutputPowerfactorSeven OBJECT-TYPE
    SYNTAX      DisplayString
    MAX-ACCESS  read-only
    STATUS      current
    DESCRIPTION
	"The ouput power factor of slave1." 
	::= { slave1OutputPowerfactor 7}	
	
slave1OutputPowerfactorEight OBJECT-TYPE
    SYNTAX      DisplayString
    MAX-ACCESS  read-only
    STATUS      current
    DESCRIPTION
	"The ouput power factor of slave1." 
	::= { slave1OutputPowerfactor 8}
	
slave1OutputPowerfactorNine OBJECT-TYPE
    SYNTAX      DisplayString
    MAX-ACCESS  read-only
    STATUS      current
    DESCRIPTION
	"The ouput power factor of slave1." 
	::= { slave1OutputPowerfactor 9}
		
slave1OutputPowerfactorTen OBJECT-TYPE
    SYNTAX      DisplayString
    MAX-ACCESS  read-only
    STATUS      current
    DESCRIPTION
	"The ouput power factor of slave1." 
	::= { slave1OutputPowerfactor 10}
		
slave1OutputPowerfactorEleven OBJECT-TYPE
    SYNTAX      DisplayString
    MAX-ACCESS  read-only
    STATUS      current
    DESCRIPTION
	"The ouput power factor of slave1." 
	::= { slave1OutputPowerfactor 11}
		
slave1OutputPowerfactorTwel OBJECT-TYPE
    SYNTAX      DisplayString
    MAX-ACCESS  read-only
    STATUS      current
    DESCRIPTION
	"The ouput power factor of slave1." 
	::= { slave1OutputPowerfactor 12}
		
slave1OutputPowerfactorThirteen OBJECT-TYPE
    SYNTAX      DisplayString
    MAX-ACCESS  read-only
    STATUS      current
    DESCRIPTION
	"The ouput power factor of slave1." 
	::= { slave1OutputPowerfactor 13}
		
slave1OutputPowerfactorFourteen OBJECT-TYPE
    SYNTAX      DisplayString
    MAX-ACCESS  read-only
    STATUS      current
    DESCRIPTION
	"The ouput power factor of slave1." 
	::= { slave1OutputPowerfactor 14}
		
slave1OutputPowerfactorFifteen OBJECT-TYPE
    SYNTAX      DisplayString
    MAX-ACCESS  read-only
    STATUS      current
    DESCRIPTION
	"The ouput power factor of slave1." 
	::= { slave1OutputPowerfactor 15}
		
slave1OutputPowerfactorSixteen OBJECT-TYPE
    SYNTAX      DisplayString
    MAX-ACCESS  read-only
    STATUS      current
    DESCRIPTION
	"The ouput power factor of slave1." 
	::= { slave1OutputPowerfactor 16}
		
slave1OutputPowerfactorSeventeen OBJECT-TYPE
    SYNTAX      DisplayString
    MAX-ACCESS  read-only
    STATUS      current
    DESCRIPTION
	"The ouput power factor of slave1." 
	::= { slave1OutputPowerfactor 17}
		
slave1OutputPowerfactorEighteen OBJECT-TYPE
    SYNTAX      DisplayString
    MAX-ACCESS  read-only
    STATUS      current
    DESCRIPTION
	"The ouput power factor of slave1." 
	::= { slave1OutputPowerfactor 18}
		
slave1OutputPowerfactorNineteen OBJECT-TYPE
    SYNTAX      DisplayString
    MAX-ACCESS  read-only
    STATUS      current
    DESCRIPTION
	"The ouput power factor of slave1." 
	::= { slave1OutputPowerfactor 19}
		
slave1OutputPowerfactorTwenty OBJECT-TYPE
    SYNTAX      DisplayString
    MAX-ACCESS  read-only
    STATUS      current
    DESCRIPTION
	"The ouput power factor of slave1." 
	::= { slave1OutputPowerfactor 20}
		
slave1OutputPowerfactorTwentyone OBJECT-TYPE
    SYNTAX      DisplayString
    MAX-ACCESS  read-only
    STATUS      current
    DESCRIPTION
	"The ouput power factor of slave1." 
	::= { slave1OutputPowerfactor 21}
		
slave1OutputPowerfactorTwentytwo OBJECT-TYPE
    SYNTAX      DisplayString
    MAX-ACCESS  read-only
    STATUS      current
    DESCRIPTION
	"The ouput power factor of slave1." 
	::= { slave1OutputPowerfactor 22}
		
slave1OutputPowerfactorTwentythree OBJECT-TYPE
    SYNTAX      DisplayString
    MAX-ACCESS  read-only
    STATUS      current
    DESCRIPTION
	"The ouput power factor of slave1." 
	::= { slave1OutputPowerfactor 23}
		
slave1OutputPowerfactorTwentyfour OBJECT-TYPE
    SYNTAX      DisplayString
    MAX-ACCESS  read-only
    STATUS      current
    DESCRIPTION
	"The ouput power factor of slave1." 
	::= { slave1OutputPowerfactor 24}
		
slave1OutputPowerfactorTwentyfive OBJECT-TYPE
    SYNTAX      DisplayString
    MAX-ACCESS  read-only
    STATUS      current
    DESCRIPTION
	"The ouput power factor of slave1." 
	::= { slave1OutputPowerfactor 25}
		
slave1OutputPowerfactorTwentysix OBJECT-TYPE
    SYNTAX      DisplayString
    MAX-ACCESS  read-only
    STATUS      current
    DESCRIPTION
	"The ouput power factor of slave1." 
	::= { slave1OutputPowerfactor 26}
		
slave1OutputPowerfactorTwentyseven OBJECT-TYPE
    SYNTAX      DisplayString
    MAX-ACCESS  read-only
    STATUS      current
    DESCRIPTION
	"The ouput power factor of slave1." 
	::= { slave1OutputPowerfactor 27}
		
slave1OutputPowerfactorTwentyeight OBJECT-TYPE
    SYNTAX      DisplayString
    MAX-ACCESS  read-only
    STATUS      current
    DESCRIPTION
	"The ouput power factor of slave1." 
	::= { slave1OutputPowerfactor 28}
		
slave1OutputPowerfactorTwentynine OBJECT-TYPE
    SYNTAX      DisplayString
    MAX-ACCESS  read-only
    STATUS      current
    DESCRIPTION
	"The ouput power factor of slave1." 
	::= { slave1OutputPowerfactor 29}
		
slave1OutputPowerfactorThirty OBJECT-TYPE
    SYNTAX      DisplayString
    MAX-ACCESS  read-only
    STATUS      current
    DESCRIPTION
	"The ouput power factor of slave1." 
	::= { slave1OutputPowerfactor 30}
		
slave1OutputPowerfactorThirtyone OBJECT-TYPE
    SYNTAX      DisplayString
    MAX-ACCESS  read-only
    STATUS      current
    DESCRIPTION
	"The ouput power factor of slave1." 
	::= { slave1OutputPowerfactor 31}
		
slave1OutputPowerfactorThirtytwo OBJECT-TYPE
    SYNTAX      DisplayString
    MAX-ACCESS  read-only
    STATUS      current
    DESCRIPTION
	"The ouput power factor of slave1." 
	::= { slave1OutputPowerfactor 32}
		
slave1OutputPowerfactorThirtythree OBJECT-TYPE
    SYNTAX      DisplayString
    MAX-ACCESS  read-only
    STATUS      current
    DESCRIPTION
	"The ouput power factor of slave1." 
	::= { slave1OutputPowerfactor 33}	
	
slave1OutputPowerfactorThirtyfour OBJECT-TYPE
    SYNTAX      DisplayString
    MAX-ACCESS  read-only
    STATUS      current
    DESCRIPTION
	"The ouput power factor of slave1." 
	::= { slave1OutputPowerfactor 34}
	
	
slave1OutputPowerfactorThirtyfive OBJECT-TYPE
    SYNTAX      DisplayString
    MAX-ACCESS  read-only
    STATUS      current
    DESCRIPTION
	"The ouput power factor of slave1." 
	::= { slave1OutputPowerfactor 35}
		
slave1OutputPowerfactorThirtysix OBJECT-TYPE
    SYNTAX      DisplayString
    MAX-ACCESS  read-only
    STATUS      current
    DESCRIPTION
	"The ouput power factor of slave1." 
	::= { slave1OutputPowerfactor 36}
		
slave1OutputPowerfactorThirtyseven OBJECT-TYPE
    SYNTAX      DisplayString
    MAX-ACCESS  read-only
    STATUS      current
    DESCRIPTION
	"The ouput power factor of slave1." 
	::= { slave1OutputPowerfactor 37}
		
slave1OutputPowerfactorThirtyeight OBJECT-TYPE
    SYNTAX      DisplayString
    MAX-ACCESS  read-only
    STATUS      current
    DESCRIPTION
	"The ouput power factor of slave1." 
	::= { slave1OutputPowerfactor 38}
		
slave1OutputPowerfactorThirtynine OBJECT-TYPE
    SYNTAX      DisplayString
    MAX-ACCESS  read-only
    STATUS      current
    DESCRIPTION
	"The ouput power factor of slave1." 
	::= { slave1OutputPowerfactor 39}
		
slave1OutputPowerfactorFourty OBJECT-TYPE
    SYNTAX      DisplayString
    MAX-ACCESS  read-only
    STATUS      current
    DESCRIPTION
	"The ouput power factor of slave1." 
	::= { slave1OutputPowerfactor 40}
		
slave1OutputPowerfactorFourtyone OBJECT-TYPE
    SYNTAX      DisplayString
    MAX-ACCESS  read-only
    STATUS      current
    DESCRIPTION
	"The ouput power factor of slave1." 
	::= { slave1OutputPowerfactor 41}
		
slave1OutputPowerfactorFourtytwo OBJECT-TYPE
    SYNTAX      DisplayString
    MAX-ACCESS  read-only
    STATUS      current
    DESCRIPTION
	"The ouput power factor of slave1." 
	::= { slave1OutputPowerfactor 42}	
	
-------------------------------slave1 output energy------------------------	
slave1OutputEnergy OBJECT IDENTIFIER ::= { slave1 10}

slave1OutputEnergyOne OBJECT-TYPE
    SYNTAX      DisplayString
    MAX-ACCESS  read-only
    STATUS      current
    DESCRIPTION
	"The ouput power of slave1." 
	::= { slave1OutputEnergy 1}

slave1OutputEnergyTwo OBJECT-TYPE
    SYNTAX      DisplayString
    MAX-ACCESS  read-only
    STATUS      current
    DESCRIPTION
	"The ouput power of slave1." 
	::= { slave1OutputEnergy 2}
	
slave1OutputEnergyThree OBJECT-TYPE
    SYNTAX      DisplayString
    MAX-ACCESS  read-only
    STATUS      current
    DESCRIPTION
	"The ouput power of slave1." 
	::= { slave1OutputEnergy 3}
	
slave1OutputEnergyFour OBJECT-TYPE
    SYNTAX      DisplayString
    MAX-ACCESS  read-only
    STATUS      current
    DESCRIPTION
	"The ouput power of slave1." 
	::= { slave1OutputEnergy 4}
		
slave1OutputEnergyFive OBJECT-TYPE
    SYNTAX      DisplayString
    MAX-ACCESS  read-only
    STATUS      current
    DESCRIPTION
	"The ouput power of slave1." 
	::= { slave1OutputEnergy 5}
	
slave1OutputEnergySix OBJECT-TYPE
    SYNTAX      DisplayString
    MAX-ACCESS  read-only
    STATUS      current
    DESCRIPTION
	"The ouput power of slave1." 
	::= { slave1OutputEnergy 6}
	
slave1OutputEnergySeven OBJECT-TYPE
    SYNTAX      DisplayString
    MAX-ACCESS  read-only
    STATUS      current
    DESCRIPTION
	"The ouput power of slave1." 
	::= { slave1OutputEnergy 7}	
	
slave1OutputEnergyEight OBJECT-TYPE
    SYNTAX      DisplayString
    MAX-ACCESS  read-only
    STATUS      current
    DESCRIPTION
	"The ouput power of slave1." 
	::= { slave1OutputEnergy 8}
	
slave1OutputEnergyNine OBJECT-TYPE
    SYNTAX      DisplayString
    MAX-ACCESS  read-only
    STATUS      current
    DESCRIPTION
	"The ouput power of slave1." 
	::= { slave1OutputEnergy 9}
		
slave1OutputEnergyTen OBJECT-TYPE
    SYNTAX      DisplayString
    MAX-ACCESS  read-only
    STATUS      current
    DESCRIPTION
	"The ouput power of slave1." 
	::= { slave1OutputEnergy 10}
		
slave1OutputEnergyEleven OBJECT-TYPE
    SYNTAX      DisplayString
    MAX-ACCESS  read-only
    STATUS      current
    DESCRIPTION
	"The ouput power of slave1." 
	::= { slave1OutputEnergy 11}
		
slave1OutputEnergyTwel OBJECT-TYPE
    SYNTAX      DisplayString
    MAX-ACCESS  read-only
    STATUS      current
    DESCRIPTION
	"The ouput power of slave1." 
	::= { slave1OutputEnergy 12}
		
slave1OutputEnergyThirteen OBJECT-TYPE
    SYNTAX      DisplayString
    MAX-ACCESS  read-only
    STATUS      current
    DESCRIPTION
	"The ouput power of slave1." 
	::= { slave1OutputEnergy 13}
		
slave1OutputEnergyFourteen OBJECT-TYPE
    SYNTAX      DisplayString
    MAX-ACCESS  read-only
    STATUS      current
    DESCRIPTION
	"The ouput power of slave1." 
	::= { slave1OutputEnergy 14}
		
slave1OutputEnergyFifteen OBJECT-TYPE
    SYNTAX      DisplayString
    MAX-ACCESS  read-only
    STATUS      current
    DESCRIPTION
	"The ouput power of slave1." 
	::= { slave1OutputEnergy 15}
		
slave1OutputEnergySixteen OBJECT-TYPE
    SYNTAX      DisplayString
    MAX-ACCESS  read-only
    STATUS      current
    DESCRIPTION
	"The ouput power of slave1." 
	::= { slave1OutputEnergy 16}
		
slave1OutputEnergySeventeen OBJECT-TYPE
    SYNTAX      DisplayString
    MAX-ACCESS  read-only
    STATUS      current
    DESCRIPTION
	"The ouput power of slave1." 
	::= { slave1OutputEnergy 17}
		
slave1OutputEnergyEighteen OBJECT-TYPE
    SYNTAX      DisplayString
    MAX-ACCESS  read-only
    STATUS      current
    DESCRIPTION
	"The ouput power of slave1." 
	::= { slave1OutputEnergy 18}
		
slave1OutputEnergyNineteen OBJECT-TYPE
    SYNTAX      DisplayString
    MAX-ACCESS  read-only
    STATUS      current
    DESCRIPTION
	"The ouput power of slave1." 
	::= { slave1OutputEnergy 19}
		
slave1OutputEnergyTwenty OBJECT-TYPE
    SYNTAX      DisplayString
    MAX-ACCESS  read-only
    STATUS      current
    DESCRIPTION
	"The ouput power of slave1." 
	::= { slave1OutputEnergy 20}
		
slave1OutputEnergyTwentyone OBJECT-TYPE
    SYNTAX      DisplayString
    MAX-ACCESS  read-only
    STATUS      current
    DESCRIPTION
	"The ouput power of slave1." 
	::= { slave1OutputEnergy 21}
		
slave1OutputEnergyTwentytwo OBJECT-TYPE
    SYNTAX      DisplayString
    MAX-ACCESS  read-only
    STATUS      current
    DESCRIPTION
	"The ouput power of slave1." 
	::= { slave1OutputEnergy 22}
		
slave1OutputEnergyTwentythree OBJECT-TYPE
    SYNTAX      DisplayString
    MAX-ACCESS  read-only
    STATUS      current
    DESCRIPTION
	"The ouput power of slave1." 
	::= { slave1OutputEnergy 23}
		
slave1OutputEnergyTwentyfour OBJECT-TYPE
    SYNTAX      DisplayString
    MAX-ACCESS  read-only
    STATUS      current
    DESCRIPTION
	"The ouput power of slave1." 
	::= { slave1OutputEnergy 24}
		
slave1OutputEnergyTwentyfive OBJECT-TYPE
    SYNTAX      DisplayString
    MAX-ACCESS  read-only
    STATUS      current
    DESCRIPTION
	"The ouput power of slave1." 
	::= { slave1OutputEnergy 25}
		
slave1OutputEnergyTwentysix OBJECT-TYPE
    SYNTAX      DisplayString
    MAX-ACCESS  read-only
    STATUS      current
    DESCRIPTION
	"The ouput power of slave1." 
	::= { slave1OutputEnergy 26}
		
slave1OutputEnergyTwentyseven OBJECT-TYPE
    SYNTAX      DisplayString
    MAX-ACCESS  read-only
    STATUS      current
    DESCRIPTION
	"The ouput power of slave1." 
	::= { slave1OutputEnergy 27}
		
slave1OutputEnergyTwentyeight OBJECT-TYPE
    SYNTAX      DisplayString
    MAX-ACCESS  read-only
    STATUS      current
    DESCRIPTION
	"The ouput power of slave1." 
	::= { slave1OutputEnergy 28}
		
slave1OutputEnergyTwentynine OBJECT-TYPE
    SYNTAX      DisplayString
    MAX-ACCESS  read-only
    STATUS      current
    DESCRIPTION
	"The ouput power of slave1." 
	::= { slave1OutputEnergy 29}
		
slave1OutputEnergyThirty OBJECT-TYPE
    SYNTAX      DisplayString
    MAX-ACCESS  read-only
    STATUS      current
    DESCRIPTION
	"The ouput power of slave1." 
	::= { slave1OutputEnergy 30}
		
slave1OutputEnergyThirtyone OBJECT-TYPE
    SYNTAX      DisplayString
    MAX-ACCESS  read-only
    STATUS      current
    DESCRIPTION
	"The ouput power of slave1." 
	::= { slave1OutputEnergy 31}
		
slave1OutputEnergyThirtytwo OBJECT-TYPE
    SYNTAX      DisplayString
    MAX-ACCESS  read-only
    STATUS      current
    DESCRIPTION
	"The ouput power of slave1." 
	::= { slave1OutputEnergy 32}
		
slave1OutputEnergyThirtythree OBJECT-TYPE
    SYNTAX      DisplayString
    MAX-ACCESS  read-only
    STATUS      current
    DESCRIPTION
	"The ouput power of slave1." 
	::= { slave1OutputEnergy 33}	
	
slave1OutputEnergyThirtyfour OBJECT-TYPE
    SYNTAX      DisplayString
    MAX-ACCESS  read-only
    STATUS      current
    DESCRIPTION
	"The ouput power of slave1." 
	::= { slave1OutputEnergy 34}
	
	
slave1OutputEnergyThirtyfive OBJECT-TYPE
    SYNTAX      DisplayString
    MAX-ACCESS  read-only
    STATUS      current
    DESCRIPTION
	"The ouput power of slave1." 
	::= { slave1OutputEnergy 35}
		
slave1OutputEnergyThirtysix OBJECT-TYPE
    SYNTAX      DisplayString
    MAX-ACCESS  read-only
    STATUS      current
    DESCRIPTION
	"The ouput power of slave1." 
	::= { slave1OutputEnergy 36}
		
slave1OutputEnergyThirtyseven OBJECT-TYPE
    SYNTAX      DisplayString
    MAX-ACCESS  read-only
    STATUS      current
    DESCRIPTION
	"The ouput power of slave1." 
	::= { slave1OutputEnergy 37}
		
slave1OutputEnergyThirtyeight OBJECT-TYPE
    SYNTAX      DisplayString
    MAX-ACCESS  read-only
    STATUS      current
    DESCRIPTION
	"The ouput power of slave1." 
	::= { slave1OutputEnergy 38}
		
slave1OutputEnergyThirtynine OBJECT-TYPE
    SYNTAX      DisplayString
    MAX-ACCESS  read-only
    STATUS      current
    DESCRIPTION
	"The ouput power of slave1." 
	::= { slave1OutputEnergy 39}
		
slave1OutputEnergyFourty OBJECT-TYPE
    SYNTAX      DisplayString
    MAX-ACCESS  read-only
    STATUS      current
    DESCRIPTION
	"The ouput power of slave1." 
	::= { slave1OutputEnergy 40}
		
slave1OutputEnergyFourtyone OBJECT-TYPE
    SYNTAX      DisplayString
    MAX-ACCESS  read-only
    STATUS      current
    DESCRIPTION
	"The ouput power of slave1." 
	::= { slave1OutputEnergy 41}
		
slave1OutputEnergyFourtytwo OBJECT-TYPE
    SYNTAX      DisplayString
    MAX-ACCESS  read-only
    STATUS      current
    DESCRIPTION
	"The ouput power of slave1." 
	::= { slave1OutputEnergy 42}	
		
	
	
	
-------------------------------slave2 information--------------------
slave2 OBJECT IDENTIFIER ::= { pdu 3}
slave2Information OBJECT IDENTIFIER ::= { slave2 1}
slave2Name OBJECT-TYPE
    SYNTAX      DisplayString
    MAX-ACCESS  read-write
    STATUS      current
    DESCRIPTION
	"This is the first device."
    ::= { slave2Information 1}
    
slave2Type OBJECT-TYPE
    SYNTAX      DisplayString
    MAX-ACCESS  read-only
    STATUS      current
    DESCRIPTION
	"This is device type "
    ::= { slave2Information 2}
    
slave2OutputNumber OBJECT-TYPE 
    SYNTAX      Integer32
    MAX-ACCESS  read-only
    STATUS      current
    DESCRIPTION
	"This is the number of output bits"
	::= { slave2Information 3}
	
slave2MacAdress OBJECT-TYPE
    SYNTAX      DisplayString
    MAX-ACCESS  read-only
    STATUS      current
    DESCRIPTION
	"This is device MAC adress"
    ::= { slave2Information 4}	

slave2Vison OBJECT-TYPE
    SYNTAX      DisplayString
    MAX-ACCESS  read-only
    STATUS      current
    DESCRIPTION
	"This is device vison "
    ::= { slave2Information 5}

slave2Frequency OBJECT-TYPE
    SYNTAX      Integer32
    MAX-ACCESS  read-only
    STATUS      current
    DESCRIPTION
	"This is device frequency "
    ::= { slave2Information 6}
	
slave2Emission OBJECT-TYPE
    SYNTAX      DisplayString
    MAX-ACCESS  read-only
    STATUS      current
    DESCRIPTION
	"This is device emission "
    ::= { slave2Information 7}	
	
slave2RunTime OBJECT-TYPE
    SYNTAX      DisplayString
    MAX-ACCESS  read-only
    STATUS      current
    DESCRIPTION
	"This is device running time "
    ::= { slave2Information 8}	

slave2BuzzerSwitch OBJECT-TYPE
    SYNTAX      DisplayString
    MAX-ACCESS  read-write
    STATUS      current
    DESCRIPTION
	"This is device buzzer switch."
    ::= { slave2Information 9}	

	
-------------------------------slave2 phase--------------------
slave2Phase OBJECT IDENTIFIER ::= { slave2 2}	
	
slave2PhaseOne OBJECT IDENTIFIER ::= { slave2Phase 1}	    
slave2PhaseOneCurrent OBJECT-TYPE
    SYNTAX      DisplayString
    MAX-ACCESS  read-only
    STATUS      current
    DESCRIPTION
	"The power of phase one"
    ::= { slave2PhaseOne 1}

slave2PhaseOneVoltage OBJECT-TYPE
    SYNTAX      DisplayString
    MAX-ACCESS  read-only
    STATUS      current
    DESCRIPTION
	"The power of phase one"
    ::= { slave2PhaseOne 2}

slave2PhaseOnePower OBJECT-TYPE
    SYNTAX      DisplayString
    MAX-ACCESS  read-only
    STATUS      current
    DESCRIPTION
	"The power of phase one"
    ::= { slave2PhaseOne 3}
	
slave2PhaseOnePowerfactor OBJECT-TYPE
    SYNTAX      DisplayString
    MAX-ACCESS  read-only
    STATUS      current
    DESCRIPTION
	"The power of phase one"
    ::= { slave2PhaseOne 4}	
	
slave2PhaseOneEnergy OBJECT-TYPE
    SYNTAX      DisplayString
    MAX-ACCESS  read-only
    STATUS      current
    DESCRIPTION
	"The power of phase one"
    ::= { slave2PhaseOne 5}	
		
slave2PhaseOneCurrentMin OBJECT-TYPE
    SYNTAX      DisplayString
    MAX-ACCESS  read-write
    STATUS      current
    DESCRIPTION
	"The power of phase one"
    ::= { slave2PhaseOne 6}	
	
slave2PhaseOneCurrentMinCritical OBJECT-TYPE
    SYNTAX      DisplayString
    MAX-ACCESS  read-write
    STATUS      current
    DESCRIPTION
	"The power of phase one"
    ::= { slave2PhaseOne 7}
	
slave2PhaseOneCurrentMaxCritical OBJECT-TYPE
    SYNTAX      DisplayString
    MAX-ACCESS  read-write
    STATUS      current
    DESCRIPTION
	"The power of phase one"
    ::= { slave2PhaseOne 8}
	
slave2PhaseOneCurrentMax OBJECT-TYPE
    SYNTAX      DisplayString
    MAX-ACCESS  read-write
    STATUS      current
    DESCRIPTION
	"The power of phase one"
    ::= { slave2PhaseOne 9}
	
slave2PhaseOneVoltageMin OBJECT-TYPE
    SYNTAX      DisplayString
    MAX-ACCESS  read-write
    STATUS      current
    DESCRIPTION
	"The power of phase one"
    ::= { slave2PhaseOne 10}
	
slave2PhaseOneVoltageMinCritical OBJECT-TYPE
    SYNTAX      DisplayString
    MAX-ACCESS  read-write
    STATUS      current
    DESCRIPTION
	"The power of phase one"
    ::= { slave2PhaseOne 11}

slave2PhaseOneVoltageMaxCritical OBJECT-TYPE
    SYNTAX      DisplayString
    MAX-ACCESS  read-write
    STATUS      current
    DESCRIPTION
	"The power of phase one"
    ::= { slave2PhaseOne 12}
	
slave2PhaseOneVoltageMax OBJECT-TYPE
    SYNTAX      DisplayString
    MAX-ACCESS  read-write
    STATUS      current
    DESCRIPTION
	"The power of phase one"
    ::= { slave2PhaseOne 13}


slave2PhaseTwo OBJECT IDENTIFIER ::= { slave2Phase 2}	    
slave2PhaseTwoCurrent OBJECT-TYPE
    SYNTAX      DisplayString
    MAX-ACCESS  read-only
    STATUS      current
    DESCRIPTION
	"The power of phase one"
    ::= { slave2PhaseTwo 1}

slave2PhaseTwoVoltage OBJECT-TYPE
    SYNTAX      DisplayString
    MAX-ACCESS  read-only
    STATUS      current
    DESCRIPTION
	"The power of phase one"
    ::= { slave2PhaseTwo 2}

slave2PhaseTwoPower OBJECT-TYPE
    SYNTAX      DisplayString
    MAX-ACCESS  read-only
    STATUS      current
    DESCRIPTION
	"The power of phase one"
    ::= { slave2PhaseTwo 3}
	
slave2PhaseTwoPowerfactor OBJECT-TYPE
    SYNTAX      DisplayString
    MAX-ACCESS  read-only
    STATUS      current
    DESCRIPTION
	"The power of phase one"
    ::= { slave2PhaseTwo 4}	
	
slave2PhaseTwoEnergy OBJECT-TYPE
    SYNTAX      DisplayString
    MAX-ACCESS  read-only
    STATUS      current
    DESCRIPTION
	"The power of phase one"
    ::= { slave2PhaseTwo 5}	
		
slave2PhaseTwoCurrentMin OBJECT-TYPE
    SYNTAX      DisplayString
    MAX-ACCESS  read-write
    STATUS      current
    DESCRIPTION
	"The power of phase one"
    ::= { slave2PhaseTwo 6}	
	
slave2PhaseTwoCurrentMinCritical OBJECT-TYPE
    SYNTAX      DisplayString
    MAX-ACCESS  read-write
    STATUS      current
    DESCRIPTION
	"The power of phase one"
    ::= { slave2PhaseTwo 7}
	
slave2PhaseTwoCurrentMaxCritical OBJECT-TYPE
    SYNTAX      DisplayString
    MAX-ACCESS  read-write
    STATUS      current
    DESCRIPTION
	"The power of phase one"
    ::= { slave2PhaseTwo 8}
	
slave2PhaseTwoCurrentMax OBJECT-TYPE
    SYNTAX      DisplayString
    MAX-ACCESS  read-write
    STATUS      current
    DESCRIPTION
	"The power of phase one"
    ::= { slave2PhaseTwo 9}
	
slave2PhaseTwoVoltageMin OBJECT-TYPE
    SYNTAX      DisplayString
    MAX-ACCESS  read-write
    STATUS      current
    DESCRIPTION
	"The power of phase one"
    ::= { slave2PhaseTwo 10}
	
slave2PhaseTwoVoltageMinCritical OBJECT-TYPE
    SYNTAX      DisplayString
    MAX-ACCESS  read-write
    STATUS      current
    DESCRIPTION
	"The power of phase one"
    ::= { slave2PhaseTwo 11}

slave2PhaseTwoVoltageMaxCritical OBJECT-TYPE
    SYNTAX      DisplayString
    MAX-ACCESS  read-write
    STATUS      current
    DESCRIPTION
	"The power of phase one"
    ::= { slave2PhaseTwo 12}
	
slave2PhaseTwoVoltageMax OBJECT-TYPE
    SYNTAX      DisplayString
    MAX-ACCESS  read-write
    STATUS      current
    DESCRIPTION
	"The power of phase one"
    ::= { slave2PhaseTwo 13}
	
	
slave2PhaseThree OBJECT IDENTIFIER ::= { slave2Phase 3}	    
slave2PhaseThreeCurrent OBJECT-TYPE
    SYNTAX      DisplayString
    MAX-ACCESS  read-only
    STATUS      current
    DESCRIPTION
	"The power of phase one"
    ::= { slave2PhaseThree 1}

slave2PhaseThreeVoltage OBJECT-TYPE
    SYNTAX      DisplayString
    MAX-ACCESS  read-only
    STATUS      current
    DESCRIPTION
	"The power of phase one"
    ::= { slave2PhaseThree 2}

slave2PhaseThreePower OBJECT-TYPE
    SYNTAX      DisplayString
    MAX-ACCESS  read-only
    STATUS      current
    DESCRIPTION
	"The power of phase one"
    ::= { slave2PhaseThree 3}
	
slave2PhaseThreePowerfactor OBJECT-TYPE
    SYNTAX      DisplayString
    MAX-ACCESS  read-only
    STATUS      current
    DESCRIPTION
	"The power of phase one"
    ::= { slave2PhaseThree 4}	
	
slave2PhaseThreeEnergy OBJECT-TYPE
    SYNTAX      DisplayString
    MAX-ACCESS  read-only
    STATUS      current
    DESCRIPTION
	"The power of phase one"
    ::= { slave2PhaseThree 5}	
		
slave2PhaseThreeCurrentMin OBJECT-TYPE
    SYNTAX      DisplayString
    MAX-ACCESS  read-write
    STATUS      current
    DESCRIPTION
	"The power of phase one"
    ::= { slave2PhaseThree 6}	
	
slave2PhaseThreeCurrentMinCritical OBJECT-TYPE
    SYNTAX      DisplayString
    MAX-ACCESS  read-write
    STATUS      current
    DESCRIPTION
	"The power of phase one"
    ::= { slave2PhaseThree 7}
	
slave2PhaseThreeCurrentMaxCritical OBJECT-TYPE
    SYNTAX      DisplayString
    MAX-ACCESS  read-write
    STATUS      current
    DESCRIPTION
	"The power of phase one"
    ::= { slave2PhaseThree 8}
	
slave2PhaseThreeCurrentMax OBJECT-TYPE
    SYNTAX      DisplayString
    MAX-ACCESS  read-write
    STATUS      current
    DESCRIPTION
	"The power of phase one"
    ::= { slave2PhaseThree 9}
	
slave2PhaseThreeVoltageMin OBJECT-TYPE
    SYNTAX      DisplayString
    MAX-ACCESS  read-write
    STATUS      current
    DESCRIPTION
	"The power of phase one"
    ::= { slave2PhaseThree 10}
	
slave2PhaseThreeVoltageMinCritical OBJECT-TYPE
    SYNTAX      DisplayString
    MAX-ACCESS  read-write
    STATUS      current
    DESCRIPTION
	"The power of phase one"
    ::= { slave2PhaseThree 11}

slave2PhaseThreeVoltageMaxCritical OBJECT-TYPE
    SYNTAX      DisplayString
    MAX-ACCESS  read-write
    STATUS      current
    DESCRIPTION
	"The power of phase one"
    ::= { slave2PhaseThree 12}
	
slave2PhaseThreeVoltageMax OBJECT-TYPE
    SYNTAX      DisplayString
    MAX-ACCESS  read-write
    STATUS      current
    DESCRIPTION
	"The power of phase one"
    ::= { slave2PhaseThree 13}
	
	
-------------------------------slave2 circuit--------------------	
slave2Circuit OBJECT IDENTIFIER ::= { slave2 3}	

slave2CircuitOne OBJECT IDENTIFIER ::= { slave2Circuit 1}	    
slave2CircuitOneBreaker OBJECT-TYPE
    SYNTAX      DisplayString
    MAX-ACCESS  read-only
    STATUS      current
    DESCRIPTION
	"The power of phase one"
    ::= { slave2CircuitOne 1}
	
slave2CircuitOneManagementBit OBJECT-TYPE
    SYNTAX      DisplayString
    MAX-ACCESS  read-only
    STATUS      current
    DESCRIPTION
	"The power of phase one"
    ::= { slave2CircuitOne 2}	

slave2CircuitOneCurrent OBJECT-TYPE
    SYNTAX      DisplayString
    MAX-ACCESS  read-only
    STATUS      current
    DESCRIPTION
	"The power of phase one"
    ::= { slave2CircuitOne 3}

slave2CircuitOneVoltage OBJECT-TYPE
    SYNTAX      DisplayString
    MAX-ACCESS  read-only
    STATUS      current
    DESCRIPTION
	"The power of phase one"
    ::= { slave2CircuitOne 4}

slave2CircuitOneEnergy OBJECT-TYPE
    SYNTAX      DisplayString
    MAX-ACCESS  read-only
    STATUS      current
    DESCRIPTION
	"The power of phase one"
    ::= { slave2CircuitOne 5}	
	
slave2CircuitOnePower OBJECT-TYPE
    SYNTAX      DisplayString
    MAX-ACCESS  read-only
    STATUS      current
    DESCRIPTION
	"The power of phase one"
    ::= { slave2CircuitOne 6}
	
slave2CircuitOneCurrentMin OBJECT-TYPE
    SYNTAX      DisplayString
    MAX-ACCESS  read-write
    STATUS      current
    DESCRIPTION
	"The power of phase one"
    ::= { slave2CircuitOne 7}	
	
slave2CircuitOneCurrentMinCritical OBJECT-TYPE
    SYNTAX      DisplayString
    MAX-ACCESS  read-write
    STATUS      current
    DESCRIPTION
	"The power of phase one"
    ::= { slave2CircuitOne 8}
	
slave2CircuitOneCurrentMaxCritical OBJECT-TYPE
    SYNTAX      DisplayString
    MAX-ACCESS  read-write
    STATUS      current
    DESCRIPTION
	"The power of phase one"
    ::= { slave2CircuitOne 9}
	
slave2CircuitOneCurrentMax OBJECT-TYPE
    SYNTAX      DisplayString
    MAX-ACCESS  read-write
    STATUS      current
    DESCRIPTION
	"The power of phase one"
    ::= { slave2CircuitOne 10}
	

slave2CircuitTwo OBJECT IDENTIFIER ::= { slave2Circuit 2}	    
slave2CircuitTwoBreaker OBJECT-TYPE
    SYNTAX      DisplayString
    MAX-ACCESS  read-only
    STATUS      current
    DESCRIPTION
	"The power of phase one"
    ::= { slave2CircuitTwo 1}
	
slave2CircuitTwoManagementBit OBJECT-TYPE
    SYNTAX      DisplayString
    MAX-ACCESS  read-only
    STATUS      current
    DESCRIPTION
	"The power of phase one"
    ::= { slave2CircuitTwo 2}	

slave2CircuitTwoCurrent OBJECT-TYPE
    SYNTAX      DisplayString
    MAX-ACCESS  read-only
    STATUS      current
    DESCRIPTION
	"The power of phase one"
    ::= { slave2CircuitTwo 3}

slave2CircuitTwoVoltage OBJECT-TYPE
    SYNTAX      DisplayString
    MAX-ACCESS  read-only
    STATUS      current
    DESCRIPTION
	"The power of phase one"
    ::= { slave2CircuitTwo 4}

slave2CircuitTwoEnergy OBJECT-TYPE
    SYNTAX      DisplayString
    MAX-ACCESS  read-only
    STATUS      current
    DESCRIPTION
	"The power of phase one"
    ::= { slave2CircuitTwo 5}	
	
slave2CircuitTwoPower OBJECT-TYPE
    SYNTAX      DisplayString
    MAX-ACCESS  read-only
    STATUS      current
    DESCRIPTION
	"The power of phase one"
    ::= { slave2CircuitTwo 6}
	
slave2CircuitTwoCurrentMin OBJECT-TYPE
    SYNTAX      DisplayString
    MAX-ACCESS  read-write
    STATUS      current
    DESCRIPTION
	"The power of phase one"
    ::= { slave2CircuitTwo 7}	
	
slave2CircuitTwoCurrentMinCritical OBJECT-TYPE
    SYNTAX      DisplayString
    MAX-ACCESS  read-write
    STATUS      current
    DESCRIPTION
	"The power of phase one"
    ::= { slave2CircuitTwo 8}
	
slave2CircuitTwoCurrentMaxCritical OBJECT-TYPE
    SYNTAX      DisplayString
    MAX-ACCESS  read-write
    STATUS      current
    DESCRIPTION
	"The power of phase one"
    ::= { slave2CircuitTwo 9}
	
slave2CircuitTwoCurrentMax OBJECT-TYPE
    SYNTAX      DisplayString
    MAX-ACCESS  read-write
    STATUS      current
    DESCRIPTION
	"The power of phase one"
    ::= { slave2CircuitTwo 10}
	
	
slave2CircuitThree OBJECT IDENTIFIER ::= { slave2Circuit 3}	    
slave2CircuitThreeBreaker OBJECT-TYPE
    SYNTAX      DisplayString
    MAX-ACCESS  read-only
    STATUS      current
    DESCRIPTION
	"The power of phase one"
    ::= { slave2CircuitThree 1}
	
slave2CircuitThreeManagementBit OBJECT-TYPE
    SYNTAX      DisplayString
    MAX-ACCESS  read-only
    STATUS      current
    DESCRIPTION
	"The power of phase one"
    ::= { slave2CircuitThree 2}	

slave2CircuitThreeCurrent OBJECT-TYPE
    SYNTAX      DisplayString
    MAX-ACCESS  read-only
    STATUS      current
    DESCRIPTION
	"The power of phase one"
    ::= { slave2CircuitThree 3}

slave2CircuitThreeVoltage OBJECT-TYPE
    SYNTAX      DisplayString
    MAX-ACCESS  read-only
    STATUS      current
    DESCRIPTION
	"The power of phase one"
    ::= { slave2CircuitThree 4}

slave2CircuitThreeEnergy OBJECT-TYPE
    SYNTAX      DisplayString
    MAX-ACCESS  read-only
    STATUS      current
    DESCRIPTION
	"The power of phase one"
    ::= { slave2CircuitThree 5}	
	
slave2CircuitThreePower OBJECT-TYPE
    SYNTAX      DisplayString
    MAX-ACCESS  read-only
    STATUS      current
    DESCRIPTION
	"The power of phase one"
    ::= { slave2CircuitThree 6}
	
slave2CircuitThreeCurrentMin OBJECT-TYPE
    SYNTAX      DisplayString
    MAX-ACCESS  read-write
    STATUS      current
    DESCRIPTION
	"The power of phase one"
    ::= { slave2CircuitThree 7}	
	
slave2CircuitThreeCurrentMinCritical OBJECT-TYPE
    SYNTAX      DisplayString
    MAX-ACCESS  read-write
    STATUS      current
    DESCRIPTION
	"The power of phase one"
    ::= { slave2CircuitThree 8}
	
slave2CircuitThreeCurrentMaxCritical OBJECT-TYPE
    SYNTAX      DisplayString
    MAX-ACCESS  read-write
    STATUS      current
    DESCRIPTION
	"The power of phase one"
    ::= { slave2CircuitThree 9}
	
slave2CircuitThreeCurrentMax OBJECT-TYPE
    SYNTAX      DisplayString
    MAX-ACCESS  read-write
    STATUS      current
    DESCRIPTION
	"The power of phase one"
    ::= { slave2CircuitThree 10}
	
	
slave2CircuitFour OBJECT IDENTIFIER ::= { slave2Circuit 4}	    
slave2CircuitFourBreaker OBJECT-TYPE
    SYNTAX      DisplayString
    MAX-ACCESS  read-only
    STATUS      current
    DESCRIPTION
	"The power of phase one"
    ::= { slave2CircuitFour 1}
	
slave2CircuitFourManagementBit OBJECT-TYPE
    SYNTAX      DisplayString
    MAX-ACCESS  read-only
    STATUS      current
    DESCRIPTION
	"The power of phase one"
    ::= { slave2CircuitFour 2}	

slave2CircuitFourCurrent OBJECT-TYPE
    SYNTAX      DisplayString
    MAX-ACCESS  read-only
    STATUS      current
    DESCRIPTION
	"The power of phase one"
    ::= { slave2CircuitFour 3}

slave2CircuitFourVoltage OBJECT-TYPE
    SYNTAX      DisplayString
    MAX-ACCESS  read-only
    STATUS      current
    DESCRIPTION
	"The power of phase one"
    ::= { slave2CircuitFour 4}

slave2CircuitFourEnergy OBJECT-TYPE
    SYNTAX      DisplayString
    MAX-ACCESS  read-only
    STATUS      current
    DESCRIPTION
	"The power of phase one"
    ::= { slave2CircuitFour 5}	
	
slave2CircuitFourPower OBJECT-TYPE
    SYNTAX      DisplayString
    MAX-ACCESS  read-only
    STATUS      current
    DESCRIPTION
	"The power of phase one"
    ::= { slave2CircuitFour 6}
	
slave2CircuitFourCurrentMin OBJECT-TYPE
    SYNTAX      DisplayString
    MAX-ACCESS  read-write
    STATUS      current
    DESCRIPTION
	"The power of phase one"
    ::= { slave2CircuitFour 7}	
	
slave2CircuitFourCurrentMinCritical OBJECT-TYPE
    SYNTAX      DisplayString
    MAX-ACCESS  read-write
    STATUS      current
    DESCRIPTION
	"The power of phase one"
    ::= { slave2CircuitFour 8}
	
slave2CircuitFourCurrentMaxCritical OBJECT-TYPE
    SYNTAX      DisplayString
    MAX-ACCESS  read-write
    STATUS      current
    DESCRIPTION
	"The power of phase one"
    ::= { slave2CircuitFour 9}
	
slave2CircuitFourCurrentMax OBJECT-TYPE
    SYNTAX      DisplayString
    MAX-ACCESS  read-write
    STATUS      current
    DESCRIPTION
	"The power of phase one"
    ::= { slave2CircuitFour 10}
	
	
slave2CircuitFive OBJECT IDENTIFIER ::= { slave2Circuit 5}	    
slave2CircuitFiveBreaker OBJECT-TYPE
    SYNTAX      DisplayString
    MAX-ACCESS  read-only
    STATUS      current
    DESCRIPTION
	"The power of phase one"
    ::= { slave2CircuitFive 1}
	
slave2CircuitFiveManagementBit OBJECT-TYPE
    SYNTAX      DisplayString
    MAX-ACCESS  read-only
    STATUS      current
    DESCRIPTION
	"The power of phase one"
    ::= { slave2CircuitFive 2}	

slave2CircuitFiveCurrent OBJECT-TYPE
    SYNTAX      DisplayString
    MAX-ACCESS  read-only
    STATUS      current
    DESCRIPTION
	"The power of phase one"
    ::= { slave2CircuitFive 3}

slave2CircuitFiveVoltage OBJECT-TYPE
    SYNTAX      DisplayString
    MAX-ACCESS  read-only
    STATUS      current
    DESCRIPTION
	"The power of phase one"
    ::= { slave2CircuitFive 4}

slave2CircuitFiveEnergy OBJECT-TYPE
    SYNTAX      DisplayString
    MAX-ACCESS  read-only
    STATUS      current
    DESCRIPTION
	"The power of phase one"
    ::= { slave2CircuitFive 5}	
	
slave2CircuitFivePower OBJECT-TYPE
    SYNTAX      DisplayString
    MAX-ACCESS  read-only
    STATUS      current
    DESCRIPTION
	"The power of phase one"
    ::= { slave2CircuitFive 6}
		
slave2CircuitFiveCurrentMin OBJECT-TYPE
    SYNTAX      DisplayString
    MAX-ACCESS  read-write
    STATUS      current
    DESCRIPTION
	"The power of phase one"
    ::= { slave2CircuitFive 7}	
	
slave2CircuitFiveCurrentMinCritical OBJECT-TYPE
    SYNTAX      DisplayString
    MAX-ACCESS  read-write
    STATUS      current
    DESCRIPTION
	"The power of phase one"
    ::= { slave2CircuitFive 8}
	
slave2CircuitFiveCurrentMaxCritical OBJECT-TYPE
    SYNTAX      DisplayString
    MAX-ACCESS  read-write
    STATUS      current
    DESCRIPTION
	"The power of phase one"
    ::= { slave2CircuitFive 9}
	
slave2CircuitFiveCurrentMax OBJECT-TYPE
    SYNTAX      DisplayString
    MAX-ACCESS  read-write
    STATUS      current
    DESCRIPTION
	"The power of phase one"
    ::= { slave2CircuitFive 10}

	
slave2CircuitSix OBJECT IDENTIFIER ::= { slave2Circuit 6}	    
slave2CircuitSixBreaker OBJECT-TYPE
    SYNTAX      DisplayString
    MAX-ACCESS  read-only
    STATUS      current
    DESCRIPTION
	"The power of phase one"
    ::= { slave2CircuitSix 1}
	
slave2CircuitSixManagementBit OBJECT-TYPE
    SYNTAX      DisplayString
    MAX-ACCESS  read-only
    STATUS      current
    DESCRIPTION
	"The power of phase one"
    ::= { slave2CircuitSix 2}	

slave2CircuitSixCurrent OBJECT-TYPE
    SYNTAX      DisplayString
    MAX-ACCESS  read-only
    STATUS      current
    DESCRIPTION
	"The power of phase one"
    ::= { slave2CircuitSix 3}

slave2CircuitSixVoltage OBJECT-TYPE
    SYNTAX      DisplayString
    MAX-ACCESS  read-only
    STATUS      current
    DESCRIPTION
	"The power of phase one"
    ::= { slave2CircuitSix 4}

slave2CircuitSixEnergy OBJECT-TYPE
    SYNTAX      DisplayString
    MAX-ACCESS  read-only
    STATUS      current
    DESCRIPTION
	"The power of phase one"
    ::= { slave2CircuitSix 5}	
	
slave2CircuitSixPower OBJECT-TYPE
    SYNTAX      DisplayString
    MAX-ACCESS  read-only
    STATUS      current
    DESCRIPTION
	"The power of phase one"
    ::= { slave2CircuitSix 6}
	
slave2CircuitSixCurrentMin OBJECT-TYPE
    SYNTAX      DisplayString
    MAX-ACCESS  read-write
    STATUS      current
    DESCRIPTION
	"The power of phase one"
    ::= { slave2CircuitSix 7}	
	
slave2CircuitSixCurrentMinCritical OBJECT-TYPE
    SYNTAX      DisplayString
    MAX-ACCESS  read-write
    STATUS      current
    DESCRIPTION
	"The power of phase one"
    ::= { slave2CircuitSix 8}
	
slave2CircuitSixCurrentMaxCritical OBJECT-TYPE
    SYNTAX      DisplayString
    MAX-ACCESS  read-write
    STATUS      current
    DESCRIPTION
	"The power of phase one"
    ::= { slave2CircuitSix 9}
	
slave2CircuitSixCurrentMax OBJECT-TYPE
    SYNTAX      DisplayString
    MAX-ACCESS  read-write
    STATUS      current
    DESCRIPTION
	"The power of phase one"
    ::= { slave2CircuitSix 10}

	
-------------------------------slave2 sensor------------------------	
slave2Sensor OBJECT IDENTIFIER ::= { slave2 4}
slave2SensorTemperatureOne OBJECT-TYPE
    SYNTAX      DisplayString
    MAX-ACCESS  read-only
    STATUS      current
    DESCRIPTION
	"This is the first device."
    ::= { slave2Sensor 1}
	
slave2SensorTemperatureTwo OBJECT-TYPE
    SYNTAX      DisplayString
    MAX-ACCESS  read-only
    STATUS      current
    DESCRIPTION
	"This is the first device."
    ::= { slave2Sensor 2}

slave2SensorHumidityOne OBJECT-TYPE
    SYNTAX      DisplayString
    MAX-ACCESS  read-only
    STATUS      current
    DESCRIPTION
	"This is the first device."
    ::= { slave2Sensor 3}

slave2SensorHumidityTwo OBJECT-TYPE
    SYNTAX      DisplayString
    MAX-ACCESS  read-only
    STATUS      current
    DESCRIPTION
	"This is the first device."
    ::= { slave2Sensor 4}	

slave2SensorDoorOne OBJECT-TYPE
    SYNTAX      DisplayString
    MAX-ACCESS  read-only
    STATUS      current
    DESCRIPTION
	"This is the first device."
    ::= { slave2Sensor 5}

slave2SensorDoorTwo OBJECT-TYPE
    SYNTAX      DisplayString
    MAX-ACCESS  read-only
    STATUS      current
    DESCRIPTION
	"This is the first device."
    ::= { slave2Sensor 6}	
	
slave2SensorSmoke OBJECT-TYPE
    SYNTAX      DisplayString
    MAX-ACCESS  read-only
    STATUS      current
    DESCRIPTION
	"This is the first device."
    ::= { slave2Sensor 7}
	
slave2SensorWater OBJECT-TYPE
    SYNTAX      DisplayString
    MAX-ACCESS  read-only
    STATUS      current
    DESCRIPTION
	"This is the first device."
    ::= { slave2Sensor 8}
	
slave2SensorTemperatureOneMin OBJECT-TYPE
    SYNTAX      DisplayString
    MAX-ACCESS  read-write
    STATUS      current
    DESCRIPTION
	"This is the first device."
    ::= { slave2Sensor 9}
	
slave2SensorTemperatureOneMinCritical OBJECT-TYPE
    SYNTAX      DisplayString
    MAX-ACCESS  read-write
    STATUS      current
    DESCRIPTION
	"This is the first device."
    ::= { slave2Sensor 10}	
	
slave2SensorTemperatureOneMaxCritical OBJECT-TYPE
    SYNTAX      DisplayString
    MAX-ACCESS  read-write
    STATUS      current
    DESCRIPTION
	"This is the first device."
    ::= { slave2Sensor 11}
	
slave2SensorTemperatureOneMax OBJECT-TYPE
    SYNTAX      DisplayString
    MAX-ACCESS  read-write
    STATUS      current
    DESCRIPTION
	"This is the first device."
    ::= { slave2Sensor 12}

slave2SensorTemperatureTwoMin OBJECT-TYPE
    SYNTAX      DisplayString
    MAX-ACCESS  read-write
    STATUS      current
    DESCRIPTION
	"This is the first device."
    ::= { slave2Sensor 13}
	
slave2SensorTemperatureTwoMinCritical OBJECT-TYPE
    SYNTAX      DisplayString
    MAX-ACCESS  read-write
    STATUS      current
    DESCRIPTION
	"This is the first device."
    ::= { slave2Sensor 14}	
	
slave2SensorTemperatureTwoMaxCritical OBJECT-TYPE
    SYNTAX      DisplayString
    MAX-ACCESS  read-write
    STATUS      current
    DESCRIPTION
	"This is the first device."
    ::= { slave2Sensor 15}
	
slave2SensorTemperatureTwoMax OBJECT-TYPE
    SYNTAX      DisplayString
    MAX-ACCESS  read-write
    STATUS      current
    DESCRIPTION
	"This is the first device."
    ::= { slave2Sensor 16}
	
slave2SensorHumidityOneMin OBJECT-TYPE
    SYNTAX      DisplayString
    MAX-ACCESS  read-write
    STATUS      current
    DESCRIPTION
	"This is the first device."
    ::= { slave2Sensor 17}
	
slave2SensorHumidityOneMinCritical OBJECT-TYPE
    SYNTAX      DisplayString
    MAX-ACCESS  read-write
    STATUS      current
    DESCRIPTION
	"This is the first device."
    ::= { slave2Sensor 18}	
	
slave2SensorHumidityOneMaxCritical OBJECT-TYPE
    SYNTAX      DisplayString
    MAX-ACCESS  read-write
    STATUS      current
    DESCRIPTION
	"This is the first device."
    ::= { slave2Sensor 19}
	
slave2SensorHumidityOneMax OBJECT-TYPE
    SYNTAX      DisplayString
    MAX-ACCESS  read-write
    STATUS      current
    DESCRIPTION
	"This is the first device."
    ::= { slave2Sensor 20}

slave2SensorHumidityTwoMin OBJECT-TYPE
    SYNTAX      DisplayString
    MAX-ACCESS  read-write
    STATUS      current
    DESCRIPTION
	"This is the first device."
    ::= { slave2Sensor 21}
	
slave2SensorHumidityTwoMinCritical OBJECT-TYPE
    SYNTAX      DisplayString
    MAX-ACCESS  read-write
    STATUS      current
    DESCRIPTION
	"This is the first device."
    ::= { slave2Sensor 22}	
	
slave2SensorHumidityTwoMaxCritical OBJECT-TYPE
    SYNTAX      DisplayString
    MAX-ACCESS  read-write
    STATUS      current
    DESCRIPTION
	"This is the first device."
    ::= { slave2Sensor 23}
	
slave2SensorHumidityTwoMax OBJECT-TYPE
    SYNTAX      DisplayString
    MAX-ACCESS  read-write
    STATUS      current
    DESCRIPTION
	"This is the first device."
    ::= { slave2Sensor 24}
	
-------------------------------slave2 output name------------------------	
slave2OutputName OBJECT IDENTIFIER ::= { slave2 5}
slave2OutputNameOne OBJECT-TYPE
    SYNTAX      DisplayString
    MAX-ACCESS  read-write
    STATUS      current
    DESCRIPTION
	"The first output name of slave2"
    ::= { slave2OutputName 1}

slave2OutputNameTwo OBJECT-TYPE
    SYNTAX      DisplayString
    MAX-ACCESS  read-write
    STATUS      current
    DESCRIPTION
	"The second output name of slave2"
    ::= { slave2OutputName 2}

slave2OutputNameThree OBJECT-TYPE
    SYNTAX      DisplayString
    MAX-ACCESS  read-write
    STATUS      current
    DESCRIPTION
	"The second output name of slave2"
    ::= { slave2OutputName 3}

slave2OutputNameFour OBJECT-TYPE
    SYNTAX      DisplayString
    MAX-ACCESS  read-write
    STATUS      current
    DESCRIPTION
	"The second output name of slave2"
    ::= { slave2OutputName 4}

slave2OutputNameFive OBJECT-TYPE
    SYNTAX      DisplayString
    MAX-ACCESS  read-write
    STATUS      current
    DESCRIPTION
	"The second output name of slave2"
    ::= { slave2OutputName 5}

slave2OutputNameSix OBJECT-TYPE
    SYNTAX      DisplayString
    MAX-ACCESS  read-write
    STATUS      current
    DESCRIPTION
	"The second output name of slave2"
    ::= { slave2OutputName 6}

slave2OutputNameSeven OBJECT-TYPE
    SYNTAX      DisplayString
    MAX-ACCESS  read-write
    STATUS      current
    DESCRIPTION
	"The second output name of slave2"
    ::= { slave2OutputName 7}

slave2OutputNameEight OBJECT-TYPE
    SYNTAX      DisplayString
    MAX-ACCESS  read-write
    STATUS      current
    DESCRIPTION
	"The second output name of slave2"
    ::= { slave2OutputName 8}

slave2OutputNameNine OBJECT-TYPE
    SYNTAX      DisplayString
    MAX-ACCESS  read-write
    STATUS      current
    DESCRIPTION
	"The second output name of slave2"
    ::= { slave2OutputName 9}

slave2OutputNameTen OBJECT-TYPE
    SYNTAX      DisplayString
    MAX-ACCESS  read-write
    STATUS      current
    DESCRIPTION
	"The second output name of slave2"
    ::= { slave2OutputName 10}

slave2OutputNameEleven OBJECT-TYPE
    SYNTAX      DisplayString
    MAX-ACCESS  read-write
    STATUS      current
    DESCRIPTION
	"The second output name of slave2"
    ::= { slave2OutputName 11}

slave2OutputNameTwel OBJECT-TYPE
    SYNTAX      DisplayString
    MAX-ACCESS  read-write
    STATUS      current
    DESCRIPTION
	"The second output name of slave2"
    ::= { slave2OutputName 12}

slave2OutputNameThirteen OBJECT-TYPE
    SYNTAX      DisplayString
    MAX-ACCESS  read-write
    STATUS      current
    DESCRIPTION
	"The second output name of slave2"
    ::= { slave2OutputName 13}

slave2OutputNameFourteen OBJECT-TYPE
    SYNTAX      DisplayString
    MAX-ACCESS  read-write
    STATUS      current
    DESCRIPTION
	"The second output name of slave2"
    ::= { slave2OutputName 14}

slave2OutputNameFifteen OBJECT-TYPE
    SYNTAX      DisplayString
    MAX-ACCESS  read-write
    STATUS      current
    DESCRIPTION
	"The second output name of slave2"
    ::= { slave2OutputName 15}

slave2OutputNameSixteen OBJECT-TYPE
    SYNTAX      DisplayString
    MAX-ACCESS  read-write
    STATUS      current
    DESCRIPTION
	"The second output name of slave2"
    ::= { slave2OutputName 16}

slave2OutputNameSeventeen OBJECT-TYPE
    SYNTAX      DisplayString
    MAX-ACCESS  read-write
    STATUS      current
    DESCRIPTION
	"The second output name of slave2"
    ::= { slave2OutputName 17}

slave2OutputNameEighteen OBJECT-TYPE
    SYNTAX      DisplayString
    MAX-ACCESS  read-write
    STATUS      current
    DESCRIPTION
	"The second output name of slave2"
    ::= { slave2OutputName 18}
	
slave2OutputNameNineteen OBJECT-TYPE
    SYNTAX      DisplayString
    MAX-ACCESS  read-write
    STATUS      current
    DESCRIPTION
	"The second output name of slave2"
    ::= { slave2OutputName 19}
	
slave2OutputNametwenty OBJECT-TYPE
    SYNTAX      DisplayString
    MAX-ACCESS  read-write
    STATUS      current
    DESCRIPTION
	"The second output name of slave2"
    ::= { slave2OutputName 20}
	
slave2OutputNameTwentyone OBJECT-TYPE
    SYNTAX      DisplayString
    MAX-ACCESS  read-write
    STATUS      current
    DESCRIPTION
	"The second output name of slave2"
    ::= { slave2OutputName 21}
	
slave2OutputNameTwentyonetwo OBJECT-TYPE
    SYNTAX      DisplayString
    MAX-ACCESS  read-write
    STATUS      current
    DESCRIPTION
	"The second output name of slave2"
    ::= { slave2OutputName 22}
	
slave2OutputNameTwentythree OBJECT-TYPE
    SYNTAX      DisplayString
    MAX-ACCESS  read-write
    STATUS      current
    DESCRIPTION
	"The second output name of slave2"
    ::= { slave2OutputName 23}
	
slave2OutputNameTwentyfour OBJECT-TYPE
    SYNTAX      DisplayString
    MAX-ACCESS  read-write
    STATUS      current
    DESCRIPTION
	"The second output name of slave2"
    ::= { slave2OutputName 24}
	
slave2OutputNameTwentyfive OBJECT-TYPE
    SYNTAX      DisplayString
    MAX-ACCESS  read-write
    STATUS      current
    DESCRIPTION
	"The second output name of slave2"
    ::= { slave2OutputName 25}
	
slave2OutputNameTwentysix OBJECT-TYPE
    SYNTAX      DisplayString
    MAX-ACCESS  read-write
    STATUS      current
    DESCRIPTION
	"The second output name of slave2"
    ::= { slave2OutputName 26}
	
slave2OutputNameTwentyseven OBJECT-TYPE
    SYNTAX      DisplayString
    MAX-ACCESS  read-write
    STATUS      current
    DESCRIPTION
	"The second output name of slave2"
    ::= { slave2OutputName 27}
	
slave2OutputNameTwentyeight OBJECT-TYPE
    SYNTAX      DisplayString
    MAX-ACCESS  read-write
    STATUS      current
    DESCRIPTION
	"The second output name of slave2"
    ::= { slave2OutputName 28}	
slave2OutputNameTwentynine OBJECT-TYPE
    SYNTAX      DisplayString
    MAX-ACCESS  read-write
    STATUS      current
    DESCRIPTION
	"The second output name of slave2"
    ::= { slave2OutputName 29}
	
slave2OutputNameThirty OBJECT-TYPE
    SYNTAX      DisplayString
    MAX-ACCESS  read-write
    STATUS      current
    DESCRIPTION
	"The second output name of slave2"
    ::= { slave2OutputName 30}
	
slave2OutputNameThirtyone OBJECT-TYPE
    SYNTAX      DisplayString
    MAX-ACCESS  read-write
    STATUS      current
    DESCRIPTION
	"The second output name of slave2"
    ::= { slave2OutputName 31}
	
slave2OutputNameThirtytwo OBJECT-TYPE
    SYNTAX      DisplayString
    MAX-ACCESS  read-write
    STATUS      current
    DESCRIPTION
	"The second output name of slave2"
    ::= { slave2OutputName 32}
	
slave2OutputNameThirtythree OBJECT-TYPE
    SYNTAX      DisplayString
    MAX-ACCESS  read-write
    STATUS      current
    DESCRIPTION
	"The second output name of slave2"
    ::= { slave2OutputName 33}
	
slave2OutputNameThirtyfour OBJECT-TYPE
    SYNTAX      DisplayString
    MAX-ACCESS  read-write
    STATUS      current
    DESCRIPTION
	"The second output name of slave2"
    ::= { slave2OutputName 34}
	
slave2OutputNameThirtyfive OBJECT-TYPE
    SYNTAX      DisplayString
    MAX-ACCESS  read-write
    STATUS      current
    DESCRIPTION
	"The second output name of slave2"
    ::= { slave2OutputName 35}
	
slave2OutputNameThirtysix OBJECT-TYPE
    SYNTAX      DisplayString
    MAX-ACCESS  read-write
    STATUS      current
    DESCRIPTION
	"The second output name of slave2"
    ::= { slave2OutputName 36}
	
slave2OutputNameThirtyseven OBJECT-TYPE
    SYNTAX      DisplayString
    MAX-ACCESS  read-write
    STATUS      current
    DESCRIPTION
	"The second output name of slave2"
    ::= { slave2OutputName 37}
	
slave2OutputNameThirtyeight OBJECT-TYPE
    SYNTAX      DisplayString
    MAX-ACCESS  read-write
    STATUS      current
    DESCRIPTION
	"The second output name of slave2"
    ::= { slave2OutputName 38}
	
slave2OutputNameThirtynine OBJECT-TYPE
    SYNTAX      DisplayString
    MAX-ACCESS  read-write
    STATUS      current
    DESCRIPTION
	"The second output name of slave2"
    ::= { slave2OutputName 39}
	
slave2OutputNameFourty OBJECT-TYPE
    SYNTAX      DisplayString
    MAX-ACCESS  read-write
    STATUS      current
    DESCRIPTION
	"The second output name of slave2"
    ::= { slave2OutputName 40}
	
slave2OutputNameFourtyone OBJECT-TYPE
    SYNTAX      DisplayString
    MAX-ACCESS  read-write
    STATUS      current
    DESCRIPTION
	"The second output name of slave2"
    ::= { slave2OutputName 41}
	
slave2OutputNameFourtytwo OBJECT-TYPE
    SYNTAX      DisplayString
    MAX-ACCESS  read-write
    STATUS      current
    DESCRIPTION
	"The second output name of slave2"
    ::= { slave2OutputName 42}	

	
-------------------------------slave2 output delay------------------------	
slave2OutputDelay OBJECT IDENTIFIER ::= { slave2 6}	
slave2OutputDelayOne OBJECT-TYPE
    SYNTAX      DisplayString
    MAX-ACCESS  read-write
    STATUS      current
    DESCRIPTION
	"The first output name of slave2"
    ::= { slave2OutputDelay 1}

slave2OutputDelayTwo OBJECT-TYPE
    SYNTAX      DisplayString
    MAX-ACCESS  read-write
    STATUS      current
    DESCRIPTION
	"The second output name of slave2"
    ::= { slave2OutputDelay 2}

slave2OutputDelayThree OBJECT-TYPE
    SYNTAX      DisplayString
    MAX-ACCESS  read-write
    STATUS      current
    DESCRIPTION
	"The second output name of slave2"
    ::= { slave2OutputDelay 3}

slave2OutputDelayFour OBJECT-TYPE
    SYNTAX      DisplayString
    MAX-ACCESS  read-write
    STATUS      current
    DESCRIPTION
	"The second output name of slave2"
    ::= { slave2OutputDelay 4}

slave2OutputDelayFive OBJECT-TYPE
    SYNTAX      DisplayString
    MAX-ACCESS  read-write
    STATUS      current
    DESCRIPTION
	"The second output name of slave2"
    ::= { slave2OutputDelay 5}

slave2OutputDelaySix OBJECT-TYPE
    SYNTAX      DisplayString
    MAX-ACCESS  read-write
    STATUS      current
    DESCRIPTION
	"The second output name of slave2"
    ::= { slave2OutputDelay 6}

slave2OutputDelaySeven OBJECT-TYPE
    SYNTAX      DisplayString
    MAX-ACCESS  read-write
    STATUS      current
    DESCRIPTION
	"The second output name of slave2"
    ::= { slave2OutputDelay 7}

slave2OutputDelayEight OBJECT-TYPE
    SYNTAX      DisplayString
    MAX-ACCESS  read-write
    STATUS      current
    DESCRIPTION
	"The second output name of slave2"
    ::= { slave2OutputDelay 8}

slave2OutputDelayNine OBJECT-TYPE
    SYNTAX      DisplayString
    MAX-ACCESS  read-write
    STATUS      current
    DESCRIPTION
	"The second output name of slave2"
    ::= { slave2OutputDelay 9}

slave2OutputDelayTen OBJECT-TYPE
    SYNTAX      DisplayString
    MAX-ACCESS  read-write
    STATUS      current
    DESCRIPTION
	"The second output name of slave2"
    ::= { slave2OutputDelay 10}

slave2OutputDelayEleven OBJECT-TYPE
    SYNTAX      DisplayString
    MAX-ACCESS  read-write
    STATUS      current
    DESCRIPTION
	"The second output name of slave2"
    ::= { slave2OutputDelay 11}

slave2OutputDelayTwel OBJECT-TYPE
    SYNTAX      DisplayString
    MAX-ACCESS  read-write
    STATUS      current
    DESCRIPTION
	"The second output name of slave2"
    ::= { slave2OutputDelay 12}

slave2OutputDelayThirteen OBJECT-TYPE
    SYNTAX      DisplayString
    MAX-ACCESS  read-write
    STATUS      current
    DESCRIPTION
	"The second output name of slave2"
    ::= { slave2OutputDelay 13}

slave2OutputDelayFourteen OBJECT-TYPE
    SYNTAX      DisplayString
    MAX-ACCESS  read-write
    STATUS      current
    DESCRIPTION
	"The second output name of slave2"
    ::= { slave2OutputDelay 14}

slave2OutputDelayFifteen OBJECT-TYPE
    SYNTAX      DisplayString
    MAX-ACCESS  read-write
    STATUS      current
    DESCRIPTION
	"The second output name of slave2"
    ::= { slave2OutputDelay 15}

slave2OutputDelaySixteen OBJECT-TYPE
    SYNTAX      DisplayString
    MAX-ACCESS  read-write
    STATUS      current
    DESCRIPTION
	"The second output name of slave2"
    ::= { slave2OutputDelay 16}

slave2OutputDelaySeventeen OBJECT-TYPE
    SYNTAX      DisplayString
    MAX-ACCESS  read-write
    STATUS      current
    DESCRIPTION
	"The second output name of slave2"
    ::= { slave2OutputDelay 17}

slave2OutputDelayEighteen OBJECT-TYPE
    SYNTAX      DisplayString
    MAX-ACCESS  read-write
    STATUS      current
    DESCRIPTION
	"The second output name of slave2"
    ::= { slave2OutputDelay 18}
	
slave2OutputDelayNineteen OBJECT-TYPE
    SYNTAX      DisplayString
    MAX-ACCESS  read-write
    STATUS      current
    DESCRIPTION
	"The second output name of slave2"
    ::= { slave2OutputDelay 19}
	
slave2OutputDelaytwenty OBJECT-TYPE
    SYNTAX      DisplayString
    MAX-ACCESS  read-write
    STATUS      current
    DESCRIPTION
	"The second output name of slave2"
    ::= { slave2OutputDelay 20}
	
slave2OutputDelayTwentyone OBJECT-TYPE
    SYNTAX      DisplayString
    MAX-ACCESS  read-write
    STATUS      current
    DESCRIPTION
	"The second output name of slave2"
    ::= { slave2OutputDelay 21}
	
slave2OutputDelayTwentyonetwo OBJECT-TYPE
    SYNTAX      DisplayString
    MAX-ACCESS  read-write
    STATUS      current
    DESCRIPTION
	"The second output name of slave2"
    ::= { slave2OutputDelay 22}
	
slave2OutputDelayTwentythree OBJECT-TYPE
    SYNTAX      DisplayString
    MAX-ACCESS  read-write
    STATUS      current
    DESCRIPTION
	"The second output name of slave2"
    ::= { slave2OutputDelay 23}
	
slave2OutputDelayTwentyfour OBJECT-TYPE
    SYNTAX      DisplayString
    MAX-ACCESS  read-write
    STATUS      current
    DESCRIPTION
	"The second output name of slave2"
    ::= { slave2OutputDelay 24}
	
slave2OutputDelayTwentyfive OBJECT-TYPE
    SYNTAX      DisplayString
    MAX-ACCESS  read-write
    STATUS      current
    DESCRIPTION
	"The second output name of slave2"
    ::= { slave2OutputDelay 25}
	
slave2OutputDelayTwentysix OBJECT-TYPE
    SYNTAX      DisplayString
    MAX-ACCESS  read-write
    STATUS      current
    DESCRIPTION
	"The second output name of slave2"
    ::= { slave2OutputDelay 26}
	
slave2OutputDelayTwentyseven OBJECT-TYPE
    SYNTAX      DisplayString
    MAX-ACCESS  read-write
    STATUS      current
    DESCRIPTION
	"The second output name of slave2"
    ::= { slave2OutputDelay 27}
	
slave2OutputDelayTwentyeight OBJECT-TYPE
    SYNTAX      DisplayString
    MAX-ACCESS  read-write
    STATUS      current
    DESCRIPTION
	"The second output name of slave2"
    ::= { slave2OutputDelay 28}	
slave2OutputDelayTwentynine OBJECT-TYPE
    SYNTAX      DisplayString
    MAX-ACCESS  read-write
    STATUS      current
    DESCRIPTION
	"The second output name of slave2"
    ::= { slave2OutputDelay 29}
	
slave2OutputDelayThirty OBJECT-TYPE
    SYNTAX      DisplayString
    MAX-ACCESS  read-write
    STATUS      current
    DESCRIPTION
	"The second output name of slave2"
    ::= { slave2OutputDelay 30}
	
slave2OutputDelayThirtyone OBJECT-TYPE
    SYNTAX      DisplayString
    MAX-ACCESS  read-write
    STATUS      current
    DESCRIPTION
	"The second output name of slave2"
    ::= { slave2OutputDelay 31}
	
slave2OutputDelayThirtytwo OBJECT-TYPE
    SYNTAX      DisplayString
    MAX-ACCESS  read-write
    STATUS      current
    DESCRIPTION
	"The second output name of slave2"
    ::= { slave2OutputDelay 32}
	
slave2OutputDelayThirtythree OBJECT-TYPE
    SYNTAX      DisplayString
    MAX-ACCESS  read-write
    STATUS      current
    DESCRIPTION
	"The second output name of slave2"
    ::= { slave2OutputDelay 33}
	
slave2OutputDelayThirtyfour OBJECT-TYPE
    SYNTAX      DisplayString
    MAX-ACCESS  read-write
    STATUS      current
    DESCRIPTION
	"The second output name of slave2"
    ::= { slave2OutputDelay 34}
	
slave2OutputDelayThirtyfive OBJECT-TYPE
    SYNTAX      DisplayString
    MAX-ACCESS  read-write
    STATUS      current
    DESCRIPTION
	"The second output name of slave2"
    ::= { slave2OutputDelay 35}
	
slave2OutputDelayThirtysix OBJECT-TYPE
    SYNTAX      DisplayString
    MAX-ACCESS  read-write
    STATUS      current
    DESCRIPTION
	"The second output name of slave2"
    ::= { slave2OutputDelay 36}
	
slave2OutputDelayThirtyseven OBJECT-TYPE
    SYNTAX      DisplayString
    MAX-ACCESS  read-write
    STATUS      current
    DESCRIPTION
	"The second output name of slave2"
    ::= { slave2OutputDelay 37}
	
slave2OutputDelayThirtyeight OBJECT-TYPE
    SYNTAX      DisplayString
    MAX-ACCESS  read-write
    STATUS      current
    DESCRIPTION
	"The second output name of slave2"
    ::= { slave2OutputDelay 38}
	
slave2OutputDelayThirtynine OBJECT-TYPE
    SYNTAX      DisplayString
    MAX-ACCESS  read-write
    STATUS      current
    DESCRIPTION
	"The second output name of slave2"
    ::= { slave2OutputDelay 39}
	
slave2OutputDelayFourty OBJECT-TYPE
    SYNTAX      DisplayString
    MAX-ACCESS  read-write
    STATUS      current
    DESCRIPTION
	"The second output name of slave2"
    ::= { slave2OutputDelay 40}
	
slave2OutputDelayFourtyone OBJECT-TYPE
    SYNTAX      DisplayString
    MAX-ACCESS  read-write
    STATUS      current
    DESCRIPTION
	"The second output name of slave2"
    ::= { slave2OutputDelay 41}
	
slave2OutputDelayFourtytwo OBJECT-TYPE
    SYNTAX      DisplayString
    MAX-ACCESS  read-write
    STATUS      current
    DESCRIPTION
	"The second output name of slave2"
    ::= { slave2OutputDelay 42}

	
-------------------------------slave2 output switch------------------------	
slave2OutputSwitch OBJECT IDENTIFIER ::= { slave2 7}		
slave2OutputSwitchOne OBJECT-TYPE
    SYNTAX      DisplayString
    MAX-ACCESS  read-write
    STATUS      current
    DESCRIPTION
	"The first output name of slave2"
    ::= { slave2OutputSwitch 1}

slave2OutputSwitchTwo OBJECT-TYPE
    SYNTAX      DisplayString
    MAX-ACCESS  read-write
    STATUS      current
    DESCRIPTION
	"The second output name of slave2"
    ::= { slave2OutputSwitch 2}

slave2OutputSwitchThree OBJECT-TYPE
    SYNTAX      DisplayString
    MAX-ACCESS  read-write
    STATUS      current
    DESCRIPTION
	"The second output name of slave2"
    ::= { slave2OutputSwitch 3}

slave2OutputSwitchFour OBJECT-TYPE
    SYNTAX      DisplayString
    MAX-ACCESS  read-write
    STATUS      current
    DESCRIPTION
	"The second output name of slave2"
    ::= { slave2OutputSwitch 4}

slave2OutputSwitchFive OBJECT-TYPE
    SYNTAX      DisplayString
    MAX-ACCESS  read-write
    STATUS      current
    DESCRIPTION
	"The second output name of slave2"
    ::= { slave2OutputSwitch 5}

slave2OutputSwitchSix OBJECT-TYPE
    SYNTAX      DisplayString
    MAX-ACCESS  read-write
    STATUS      current
    DESCRIPTION
	"The second output name of slave2"
    ::= { slave2OutputSwitch 6}

slave2OutputSwitchSeven OBJECT-TYPE
    SYNTAX      DisplayString
    MAX-ACCESS  read-write
    STATUS      current
    DESCRIPTION
	"The second output name of slave2"
    ::= { slave2OutputSwitch 7}

slave2OutputSwitchEight OBJECT-TYPE
    SYNTAX      DisplayString
    MAX-ACCESS  read-write
    STATUS      current
    DESCRIPTION
	"The second output name of slave2"
    ::= { slave2OutputSwitch 8}

slave2OutputSwitchNine OBJECT-TYPE
    SYNTAX      DisplayString
    MAX-ACCESS  read-write
    STATUS      current
    DESCRIPTION
	"The second output name of slave2"
    ::= { slave2OutputSwitch 9}

slave2OutputSwitchTen OBJECT-TYPE
    SYNTAX      DisplayString
    MAX-ACCESS  read-write
    STATUS      current
    DESCRIPTION
	"The second output name of slave2"
    ::= { slave2OutputSwitch 10}

slave2OutputSwitchEleven OBJECT-TYPE
    SYNTAX      DisplayString
    MAX-ACCESS  read-write
    STATUS      current
    DESCRIPTION
	"The second output name of slave2"
    ::= { slave2OutputSwitch 11}

slave2OutputSwitchTwel OBJECT-TYPE
    SYNTAX      DisplayString
    MAX-ACCESS  read-write
    STATUS      current
    DESCRIPTION
	"The second output name of slave2"
    ::= { slave2OutputSwitch 12}

slave2OutputSwitchThirteen OBJECT-TYPE
    SYNTAX      DisplayString
    MAX-ACCESS  read-write
    STATUS      current
    DESCRIPTION
	"The second output name of slave2"
    ::= { slave2OutputSwitch 13}

slave2OutputSwitchFourteen OBJECT-TYPE
    SYNTAX      DisplayString
    MAX-ACCESS  read-write
    STATUS      current
    DESCRIPTION
	"The second output name of slave2"
    ::= { slave2OutputSwitch 14}

slave2OutputSwitchFifteen OBJECT-TYPE
    SYNTAX      DisplayString
    MAX-ACCESS  read-write
    STATUS      current
    DESCRIPTION
	"The second output name of slave2"
    ::= { slave2OutputSwitch 15}

slave2OutputSwitchSixteen OBJECT-TYPE
    SYNTAX      DisplayString
    MAX-ACCESS  read-write
    STATUS      current
    DESCRIPTION
	"The second output name of slave2"
    ::= { slave2OutputSwitch 16}

slave2OutputSwitchSeventeen OBJECT-TYPE
    SYNTAX      DisplayString
    MAX-ACCESS  read-write
    STATUS      current
    DESCRIPTION
	"The second output name of slave2"
    ::= { slave2OutputSwitch 17}

slave2OutputSwitchEighteen OBJECT-TYPE
    SYNTAX      DisplayString
    MAX-ACCESS  read-write
    STATUS      current
    DESCRIPTION
	"The second output name of slave2"
    ::= { slave2OutputSwitch 18}
	
slave2OutputSwitchNineteen OBJECT-TYPE
    SYNTAX      DisplayString
    MAX-ACCESS  read-write
    STATUS      current
    DESCRIPTION
	"The second output name of slave2"
    ::= { slave2OutputSwitch 19}
	
slave2OutputSwitchtwenty OBJECT-TYPE
    SYNTAX      DisplayString
    MAX-ACCESS  read-write
    STATUS      current
    DESCRIPTION
	"The second output name of slave2"
    ::= { slave2OutputSwitch 20}
	
slave2OutputSwitchTwentyone OBJECT-TYPE
    SYNTAX      DisplayString
    MAX-ACCESS  read-write
    STATUS      current
    DESCRIPTION
	"The second output name of slave2"
    ::= { slave2OutputSwitch 21}
	
slave2OutputSwitchTwentyonetwo OBJECT-TYPE
    SYNTAX      DisplayString
    MAX-ACCESS  read-write
    STATUS      current
    DESCRIPTION
	"The second output name of slave2"
    ::= { slave2OutputSwitch 22}
	
slave2OutputSwitchTwentythree OBJECT-TYPE
    SYNTAX      DisplayString
    MAX-ACCESS  read-write
    STATUS      current
    DESCRIPTION
	"The second output name of slave2"
    ::= { slave2OutputSwitch 23}
	
slave2OutputSwitchTwentyfour OBJECT-TYPE
    SYNTAX      DisplayString
    MAX-ACCESS  read-write
    STATUS      current
    DESCRIPTION
	"The second output name of slave2"
    ::= { slave2OutputSwitch 24}
	
slave2OutputSwitchTwentyfive OBJECT-TYPE
    SYNTAX      DisplayString
    MAX-ACCESS  read-write
    STATUS      current
    DESCRIPTION
	"The second output name of slave2"
    ::= { slave2OutputSwitch 25}
	
slave2OutputSwitchTwentysix OBJECT-TYPE
    SYNTAX      DisplayString
    MAX-ACCESS  read-write
    STATUS      current
    DESCRIPTION
	"The second output name of slave2"
    ::= { slave2OutputSwitch 26}
	
slave2OutputSwitchTwentyseven OBJECT-TYPE
    SYNTAX      DisplayString
    MAX-ACCESS  read-write
    STATUS      current
    DESCRIPTION
	"The second output name of slave2"
    ::= { slave2OutputSwitch 27}
	
slave2OutputSwitchTwentyeight OBJECT-TYPE
    SYNTAX      DisplayString
    MAX-ACCESS  read-write
    STATUS      current
    DESCRIPTION
	"The second output name of slave2"
    ::= { slave2OutputSwitch 28}	
slave2OutputSwitchTwentynine OBJECT-TYPE
    SYNTAX      DisplayString
    MAX-ACCESS  read-write
    STATUS      current
    DESCRIPTION
	"The second output name of slave2"
    ::= { slave2OutputSwitch 29}
	
slave2OutputSwitchThirty OBJECT-TYPE
    SYNTAX      DisplayString
    MAX-ACCESS  read-write
    STATUS      current
    DESCRIPTION
	"The second output name of slave2"
    ::= { slave2OutputSwitch 30}
	
slave2OutputSwitchThirtyone OBJECT-TYPE
    SYNTAX      DisplayString
    MAX-ACCESS  read-write
    STATUS      current
    DESCRIPTION
	"The second output name of slave2"
    ::= { slave2OutputSwitch 31}
	
slave2OutputSwitchThirtytwo OBJECT-TYPE
    SYNTAX      DisplayString
    MAX-ACCESS  read-write
    STATUS      current
    DESCRIPTION
	"The second output name of slave2"
    ::= { slave2OutputSwitch 32}
	
slave2OutputSwitchThirtythree OBJECT-TYPE
    SYNTAX      DisplayString
    MAX-ACCESS  read-write
    STATUS      current
    DESCRIPTION
	"The second output name of slave2"
    ::= { slave2OutputSwitch 33}
	
slave2OutputSwitchThirtyfour OBJECT-TYPE
    SYNTAX      DisplayString
    MAX-ACCESS  read-write
    STATUS      current
    DESCRIPTION
	"The second output name of slave2"
    ::= { slave2OutputSwitch 34}
	
slave2OutputSwitchThirtyfive OBJECT-TYPE
    SYNTAX      DisplayString
    MAX-ACCESS  read-write
    STATUS      current
    DESCRIPTION
	"The second output name of slave2"
    ::= { slave2OutputSwitch 35}
	
slave2OutputSwitchThirtysix OBJECT-TYPE
    SYNTAX      DisplayString
    MAX-ACCESS  read-write
    STATUS      current
    DESCRIPTION
	"The second output name of slave2"
    ::= { slave2OutputSwitch 36}
	
slave2OutputSwitchThirtyseven OBJECT-TYPE
    SYNTAX      DisplayString
    MAX-ACCESS  read-write
    STATUS      current
    DESCRIPTION
	"The second output name of slave2"
    ::= { slave2OutputSwitch 37}
	
slave2OutputSwitchThirtyeight OBJECT-TYPE
    SYNTAX      DisplayString
    MAX-ACCESS  read-write
    STATUS      current
    DESCRIPTION
	"The second output name of slave2"
    ::= { slave2OutputSwitch 38}
	
slave2OutputSwitchThirtynine OBJECT-TYPE
    SYNTAX      DisplayString
    MAX-ACCESS  read-write
    STATUS      current
    DESCRIPTION
	"The second output name of slave2"
    ::= { slave2OutputSwitch 39}
	
slave2OutputSwitchFourty OBJECT-TYPE
    SYNTAX      DisplayString
    MAX-ACCESS  read-write
    STATUS      current
    DESCRIPTION
	"The second output name of slave2"
    ::= { slave2OutputSwitch 40}
	
slave2OutputSwitchFourtyone OBJECT-TYPE
    SYNTAX      DisplayString
    MAX-ACCESS  read-write
    STATUS      current
    DESCRIPTION
	"The second output name of slave2"
    ::= { slave2OutputSwitch 41}
	
slave2OutputSwitchFourtytwo OBJECT-TYPE
    SYNTAX      DisplayString
    MAX-ACCESS  read-write
    STATUS      current
    DESCRIPTION
	"The second output name of slave2"
    ::= { slave2OutputSwitch 42}

	
-------------------------------slave2 output current------------------------	
slave2OutputCurrent OBJECT IDENTIFIER ::= { slave2 8}		
slave2OutputCurrentValue OBJECT IDENTIFIER ::= { slave2OutputCurrent 1}	

slave2OutputCurrentValueOne OBJECT-TYPE
    SYNTAX      DisplayString
    MAX-ACCESS  read-write
    STATUS      current
    DESCRIPTION
	"The first output name of slave2"
    ::= { slave2OutputCurrentValue 1}

slave2OutputCurrentValueTwo OBJECT-TYPE
    SYNTAX      DisplayString
    MAX-ACCESS  read-write
    STATUS      current
    DESCRIPTION
	"The second output name of slave2"
    ::= { slave2OutputCurrentValue 2}

slave2OutputCurrentValueThree OBJECT-TYPE
    SYNTAX      DisplayString
    MAX-ACCESS  read-write
    STATUS      current
    DESCRIPTION
	"The second output name of slave2"
    ::= { slave2OutputCurrentValue 3}

slave2OutputCurrentValueFour OBJECT-TYPE
    SYNTAX      DisplayString
    MAX-ACCESS  read-write
    STATUS      current
    DESCRIPTION
	"The second output name of slave2"
    ::= { slave2OutputCurrentValue 4}

slave2OutputCurrentValueFive OBJECT-TYPE
    SYNTAX      DisplayString
    MAX-ACCESS  read-write
    STATUS      current
    DESCRIPTION
	"The second output name of slave2"
    ::= { slave2OutputCurrentValue 5}

slave2OutputCurrentValueSix OBJECT-TYPE
    SYNTAX      DisplayString
    MAX-ACCESS  read-write
    STATUS      current
    DESCRIPTION
	"The second output name of slave2"
    ::= { slave2OutputCurrentValue 6}

slave2OutputCurrentValueSeven OBJECT-TYPE
    SYNTAX      DisplayString
    MAX-ACCESS  read-write
    STATUS      current
    DESCRIPTION
	"The second output name of slave2"
    ::= { slave2OutputCurrentValue 7}

slave2OutputCurrentValueEight OBJECT-TYPE
    SYNTAX      DisplayString
    MAX-ACCESS  read-write
    STATUS      current
    DESCRIPTION
	"The second output name of slave2"
    ::= { slave2OutputCurrentValue 8}

slave2OutputCurrentValueNine OBJECT-TYPE
    SYNTAX      DisplayString
    MAX-ACCESS  read-write
    STATUS      current
    DESCRIPTION
	"The second output name of slave2"
    ::= { slave2OutputCurrentValue 9}

slave2OutputCurrentValueTen OBJECT-TYPE
    SYNTAX      DisplayString
    MAX-ACCESS  read-write
    STATUS      current
    DESCRIPTION
	"The second output name of slave2"
    ::= { slave2OutputCurrentValue 10}

slave2OutputCurrentValueEleven OBJECT-TYPE
    SYNTAX      DisplayString
    MAX-ACCESS  read-write
    STATUS      current
    DESCRIPTION
	"The second output name of slave2"
    ::= { slave2OutputCurrentValue 11}

slave2OutputCurrentValueTwel OBJECT-TYPE
    SYNTAX      DisplayString
    MAX-ACCESS  read-write
    STATUS      current
    DESCRIPTION
	"The second output name of slave2"
    ::= { slave2OutputCurrentValue 12}

slave2OutputCurrentValueThirteen OBJECT-TYPE
    SYNTAX      DisplayString
    MAX-ACCESS  read-write
    STATUS      current
    DESCRIPTION
	"The second output name of slave2"
    ::= { slave2OutputCurrentValue 13}

slave2OutputCurrentValueFourteen OBJECT-TYPE
    SYNTAX      DisplayString
    MAX-ACCESS  read-write
    STATUS      current
    DESCRIPTION
	"The second output name of slave2"
    ::= { slave2OutputCurrentValue 14}

slave2OutputCurrentValueFifteen OBJECT-TYPE
    SYNTAX      DisplayString
    MAX-ACCESS  read-write
    STATUS      current
    DESCRIPTION
	"The second output name of slave2"
    ::= { slave2OutputCurrentValue 15}

slave2OutputCurrentValueSixteen OBJECT-TYPE
    SYNTAX      DisplayString
    MAX-ACCESS  read-write
    STATUS      current
    DESCRIPTION
	"The second output name of slave2"
    ::= { slave2OutputCurrentValue 16}

slave2OutputCurrentValueSeventeen OBJECT-TYPE
    SYNTAX      DisplayString
    MAX-ACCESS  read-write
    STATUS      current
    DESCRIPTION
	"The second output name of slave2"
    ::= { slave2OutputCurrentValue 17}

slave2OutputCurrentValueEighteen OBJECT-TYPE
    SYNTAX      DisplayString
    MAX-ACCESS  read-write
    STATUS      current
    DESCRIPTION
	"The second output name of slave2"
    ::= { slave2OutputCurrentValue 18}
	
slave2OutputCurrentValueNineteen OBJECT-TYPE
    SYNTAX      DisplayString
    MAX-ACCESS  read-write
    STATUS      current
    DESCRIPTION
	"The second output name of slave2"
    ::= { slave2OutputCurrentValue 19}
	
slave2OutputCurrentValuetwenty OBJECT-TYPE
    SYNTAX      DisplayString
    MAX-ACCESS  read-write
    STATUS      current
    DESCRIPTION
	"The second output name of slave2"
    ::= { slave2OutputCurrentValue 20}
	
slave2OutputCurrentValueTwentyone OBJECT-TYPE
    SYNTAX      DisplayString
    MAX-ACCESS  read-write
    STATUS      current
    DESCRIPTION
	"The second output name of slave2"
    ::= { slave2OutputCurrentValue 21}
	
slave2OutputCurrentValueTwentyonetwo OBJECT-TYPE
    SYNTAX      DisplayString
    MAX-ACCESS  read-write
    STATUS      current
    DESCRIPTION
	"The second output name of slave2"
    ::= { slave2OutputCurrentValue 22}
	
slave2OutputCurrentValueTwentythree OBJECT-TYPE
    SYNTAX      DisplayString
    MAX-ACCESS  read-write
    STATUS      current
    DESCRIPTION
	"The second output name of slave2"
    ::= { slave2OutputCurrentValue 23}
	
slave2OutputCurrentValueTwentyfour OBJECT-TYPE
    SYNTAX      DisplayString
    MAX-ACCESS  read-write
    STATUS      current
    DESCRIPTION
	"The second output name of slave2"
    ::= { slave2OutputCurrentValue 24}
	
slave2OutputCurrentValueTwentyfive OBJECT-TYPE
    SYNTAX      DisplayString
    MAX-ACCESS  read-write
    STATUS      current
    DESCRIPTION
	"The second output name of slave2"
    ::= { slave2OutputCurrentValue 25}
	
slave2OutputCurrentValueTwentysix OBJECT-TYPE
    SYNTAX      DisplayString
    MAX-ACCESS  read-write
    STATUS      current
    DESCRIPTION
	"The second output name of slave2"
    ::= { slave2OutputCurrentValue 26}
	
slave2OutputCurrentValueTwentyseven OBJECT-TYPE
    SYNTAX      DisplayString
    MAX-ACCESS  read-write
    STATUS      current
    DESCRIPTION
	"The second output name of slave2"
    ::= { slave2OutputCurrentValue 27}
	
slave2OutputCurrentValueTwentyeight OBJECT-TYPE
    SYNTAX      DisplayString
    MAX-ACCESS  read-write
    STATUS      current
    DESCRIPTION
	"The second output name of slave2"
    ::= { slave2OutputCurrentValue 28}	
slave2OutputCurrentValueTwentynine OBJECT-TYPE
    SYNTAX      DisplayString
    MAX-ACCESS  read-write
    STATUS      current
    DESCRIPTION
	"The second output name of slave2"
    ::= { slave2OutputCurrentValue 29}
	
slave2OutputCurrentValueThirty OBJECT-TYPE
    SYNTAX      DisplayString
    MAX-ACCESS  read-write
    STATUS      current
    DESCRIPTION
	"The second output name of slave2"
    ::= { slave2OutputCurrentValue 30}
	
slave2OutputCurrentValueThirtyone OBJECT-TYPE
    SYNTAX      DisplayString
    MAX-ACCESS  read-write
    STATUS      current
    DESCRIPTION
	"The second output name of slave2"
    ::= { slave2OutputCurrentValue 31}
	
slave2OutputCurrentValueThirtytwo OBJECT-TYPE
    SYNTAX      DisplayString
    MAX-ACCESS  read-write
    STATUS      current
    DESCRIPTION
	"The second output name of slave2"
    ::= { slave2OutputCurrentValue 32}
	
slave2OutputCurrentValueThirtythree OBJECT-TYPE
    SYNTAX      DisplayString
    MAX-ACCESS  read-write
    STATUS      current
    DESCRIPTION
	"The second output name of slave2"
    ::= { slave2OutputCurrentValue 33}
	
slave2OutputCurrentValueThirtyfour OBJECT-TYPE
    SYNTAX      DisplayString
    MAX-ACCESS  read-write
    STATUS      current
    DESCRIPTION
	"The second output name of slave2"
    ::= { slave2OutputCurrentValue 34}
	
slave2OutputCurrentValueThirtyfive OBJECT-TYPE
    SYNTAX      DisplayString
    MAX-ACCESS  read-write
    STATUS      current
    DESCRIPTION
	"The second output name of slave2"
    ::= { slave2OutputCurrentValue 35}
	
slave2OutputCurrentValueThirtysix OBJECT-TYPE
    SYNTAX      DisplayString
    MAX-ACCESS  read-write
    STATUS      current
    DESCRIPTION
	"The second output name of slave2"
    ::= { slave2OutputCurrentValue 36}
	
slave2OutputCurrentValueThirtyseven OBJECT-TYPE
    SYNTAX      DisplayString
    MAX-ACCESS  read-write
    STATUS      current
    DESCRIPTION
	"The second output name of slave2"
    ::= { slave2OutputCurrentValue 37}
	
slave2OutputCurrentValueThirtyeight OBJECT-TYPE
    SYNTAX      DisplayString
    MAX-ACCESS  read-write
    STATUS      current
    DESCRIPTION
	"The second output name of slave2"
    ::= { slave2OutputCurrentValue 38}
	
slave2OutputCurrentValueThirtynine OBJECT-TYPE
    SYNTAX      DisplayString
    MAX-ACCESS  read-write
    STATUS      current
    DESCRIPTION
	"The second output name of slave2"
    ::= { slave2OutputCurrentValue 39}
	
slave2OutputCurrentValueFourty OBJECT-TYPE
    SYNTAX      DisplayString
    MAX-ACCESS  read-write
    STATUS      current
    DESCRIPTION
	"The second output name of slave2"
    ::= { slave2OutputCurrentValue 40}
	
slave2OutputCurrentValueFourtyone OBJECT-TYPE
    SYNTAX      DisplayString
    MAX-ACCESS  read-write
    STATUS      current
    DESCRIPTION
	"The second output name of slave2"
    ::= { slave2OutputCurrentValue 41}
	
slave2OutputCurrentValueFourtytwo OBJECT-TYPE
    SYNTAX      DisplayString
    MAX-ACCESS  read-write
    STATUS      current
    DESCRIPTION
	"The second output name of slave2"
    ::= { slave2OutputCurrentValue 42}


-------------------------------slave2 output current Min------------------------			
slave2OutputCurrentMin OBJECT IDENTIFIER ::= { slave2OutputCurrent 2}	

slave2OutputCurrentMinOne OBJECT-TYPE
    SYNTAX      DisplayString
    MAX-ACCESS  read-write
    STATUS      current
    DESCRIPTION
	"The first output Min. current alarm value of slave2"
    ::= { slave2OutputCurrentMin 1}

slave2OutputCurrentMinTwo OBJECT-TYPE
    SYNTAX      DisplayString
    MAX-ACCESS  read-write
    STATUS      current
    DESCRIPTION
	"The second output Min. current alarm value of slave2"
    ::= { slave2OutputCurrentMin 2}

slave2OutputCurrentMinThree OBJECT-TYPE
    SYNTAX      DisplayString
    MAX-ACCESS  read-write
    STATUS      current
    DESCRIPTION
	"The second output Min. current alarm value of slave2"
    ::= { slave2OutputCurrentMin 3}

slave2OutputCurrentMinFour OBJECT-TYPE
    SYNTAX      DisplayString
    MAX-ACCESS  read-write
    STATUS      current
    DESCRIPTION
	"The second output Min. current alarm value of slave2"
    ::= { slave2OutputCurrentMin 4}

slave2OutputCurrentMinFive OBJECT-TYPE
    SYNTAX      DisplayString
    MAX-ACCESS  read-write
    STATUS      current
    DESCRIPTION
	"The second output Min. current alarm value of slave2"
    ::= { slave2OutputCurrentMin 5}

slave2OutputCurrentMinSix OBJECT-TYPE
    SYNTAX      DisplayString
    MAX-ACCESS  read-write
    STATUS      current
    DESCRIPTION
	"The second output Min. current alarm value of slave2"
    ::= { slave2OutputCurrentMin 6}

slave2OutputCurrentMinSeven OBJECT-TYPE
    SYNTAX      DisplayString
    MAX-ACCESS  read-write
    STATUS      current
    DESCRIPTION
	"The second output Min. current alarm value of slave2"
    ::= { slave2OutputCurrentMin 7}

slave2OutputCurrentMinEight OBJECT-TYPE
    SYNTAX      DisplayString
    MAX-ACCESS  read-write
    STATUS      current
    DESCRIPTION
	"The second output Min. current alarm value of slave2"
    ::= { slave2OutputCurrentMin 8}

slave2OutputCurrentMinNine OBJECT-TYPE
    SYNTAX      DisplayString
    MAX-ACCESS  read-write
    STATUS      current
    DESCRIPTION
	"The second output Min. current alarm value of slave2"
    ::= { slave2OutputCurrentMin 9}

slave2OutputCurrentMinTen OBJECT-TYPE
    SYNTAX      DisplayString
    MAX-ACCESS  read-write
    STATUS      current
    DESCRIPTION
	"The second output Min. current alarm value of slave2"
    ::= { slave2OutputCurrentMin 10}

slave2OutputCurrentMinEleven OBJECT-TYPE
    SYNTAX      DisplayString
    MAX-ACCESS  read-write
    STATUS      current
    DESCRIPTION
	"The second output Min. current alarm value of slave2"
    ::= { slave2OutputCurrentMin 11}

slave2OutputCurrentMinTwel OBJECT-TYPE
    SYNTAX      DisplayString
    MAX-ACCESS  read-write
    STATUS      current
    DESCRIPTION
	"The second output Min. current alarm value of slave2"
    ::= { slave2OutputCurrentMin 12}

slave2OutputCurrentMinThirteen OBJECT-TYPE
    SYNTAX      DisplayString
    MAX-ACCESS  read-write
    STATUS      current
    DESCRIPTION
	"The second output Min. current alarm value of slave2"
    ::= { slave2OutputCurrentMin 13}

slave2OutputCurrentMinFourteen OBJECT-TYPE
    SYNTAX      DisplayString
    MAX-ACCESS  read-write
    STATUS      current
    DESCRIPTION
	"The second output Min. current alarm value of slave2"
    ::= { slave2OutputCurrentMin 14}

slave2OutputCurrentMinFifteen OBJECT-TYPE
    SYNTAX      DisplayString
    MAX-ACCESS  read-write
    STATUS      current
    DESCRIPTION
	"The second output Min. current alarm value of slave2"
    ::= { slave2OutputCurrentMin 15}

slave2OutputCurrentMinSixteen OBJECT-TYPE
    SYNTAX      DisplayString
    MAX-ACCESS  read-write
    STATUS      current
    DESCRIPTION
	"The second output Min. current alarm value of slave2"
    ::= { slave2OutputCurrentMin 16}

slave2OutputCurrentMinSeventeen OBJECT-TYPE
    SYNTAX      DisplayString
    MAX-ACCESS  read-write
    STATUS      current
    DESCRIPTION
	"The second output Min. current alarm value of slave2"
    ::= { slave2OutputCurrentMin 17}

slave2OutputCurrentMinEighteen OBJECT-TYPE
    SYNTAX      DisplayString
    MAX-ACCESS  read-write
    STATUS      current
    DESCRIPTION
	"The second output Min. current alarm value of slave2"
    ::= { slave2OutputCurrentMin 18}
	
slave2OutputCurrentMinNineteen OBJECT-TYPE
    SYNTAX      DisplayString
    MAX-ACCESS  read-write
    STATUS      current
    DESCRIPTION
	"The second output Min. current alarm value of slave2"
    ::= { slave2OutputCurrentMin 19}
	
slave2OutputCurrentMintwenty OBJECT-TYPE
    SYNTAX      DisplayString
    MAX-ACCESS  read-write
    STATUS      current
    DESCRIPTION
	"The second output Min. current alarm value of slave2"
    ::= { slave2OutputCurrentMin 20}
	
slave2OutputCurrentMinTwentyone OBJECT-TYPE
    SYNTAX      DisplayString
    MAX-ACCESS  read-write
    STATUS      current
    DESCRIPTION
	"The second output Min. current alarm value of slave2"
    ::= { slave2OutputCurrentMin 21}
	
slave2OutputCurrentMinTwentyonetwo OBJECT-TYPE
    SYNTAX      DisplayString
    MAX-ACCESS  read-write
    STATUS      current
    DESCRIPTION
	"The second output Min. current alarm value of slave2"
    ::= { slave2OutputCurrentMin 22}
	
slave2OutputCurrentMinTwentythree OBJECT-TYPE
    SYNTAX      DisplayString
    MAX-ACCESS  read-write
    STATUS      current
    DESCRIPTION
	"The second output Min. current alarm value of slave2"
    ::= { slave2OutputCurrentMin 23}
	
slave2OutputCurrentMinTwentyfour OBJECT-TYPE
    SYNTAX      DisplayString
    MAX-ACCESS  read-write
    STATUS      current
    DESCRIPTION
	"The second output Min. current alarm value of slave2"
    ::= { slave2OutputCurrentMin 24}
	
slave2OutputCurrentMinTwentyfive OBJECT-TYPE
    SYNTAX      DisplayString
    MAX-ACCESS  read-write
    STATUS      current
    DESCRIPTION
	"The second output Min. current alarm value of slave2"
    ::= { slave2OutputCurrentMin 25}
	
slave2OutputCurrentMinTwentysix OBJECT-TYPE
    SYNTAX      DisplayString
    MAX-ACCESS  read-write
    STATUS      current
    DESCRIPTION
	"The second output Min. current alarm value of slave2"
    ::= { slave2OutputCurrentMin 26}
	
slave2OutputCurrentMinTwentyseven OBJECT-TYPE
    SYNTAX      DisplayString
    MAX-ACCESS  read-write
    STATUS      current
    DESCRIPTION
	"The second output Min. current alarm value of slave2"
    ::= { slave2OutputCurrentMin 27}
	
slave2OutputCurrentMinTwentyeight OBJECT-TYPE
    SYNTAX      DisplayString
    MAX-ACCESS  read-write
    STATUS      current
    DESCRIPTION
	"The second output Min. current alarm value of slave2"
    ::= { slave2OutputCurrentMin 28}	
slave2OutputCurrentMinTwentynine OBJECT-TYPE
    SYNTAX      DisplayString
    MAX-ACCESS  read-write
    STATUS      current
    DESCRIPTION
	"The second output Min. current alarm value of slave2"
    ::= { slave2OutputCurrentMin 29}
	
slave2OutputCurrentMinThirty OBJECT-TYPE
    SYNTAX      DisplayString
    MAX-ACCESS  read-write
    STATUS      current
    DESCRIPTION
	"The second output Min. current alarm value of slave2"
    ::= { slave2OutputCurrentMin 30}
	
slave2OutputCurrentMinThirtyone OBJECT-TYPE
    SYNTAX      DisplayString
    MAX-ACCESS  read-write
    STATUS      current
    DESCRIPTION
	"The second output Min. current alarm value of slave2"
    ::= { slave2OutputCurrentMin 31}
	
slave2OutputCurrentMinThirtytwo OBJECT-TYPE
    SYNTAX      DisplayString
    MAX-ACCESS  read-write
    STATUS      current
    DESCRIPTION
	"The second output Min. current alarm value of slave2"
    ::= { slave2OutputCurrentMin 32}
	
slave2OutputCurrentMinThirtythree OBJECT-TYPE
    SYNTAX      DisplayString
    MAX-ACCESS  read-write
    STATUS      current
    DESCRIPTION
	"The second output Min. current alarm value of slave2"
    ::= { slave2OutputCurrentMin 33}
	
slave2OutputCurrentMinThirtyfour OBJECT-TYPE
    SYNTAX      DisplayString
    MAX-ACCESS  read-write
    STATUS      current
    DESCRIPTION
	"The second output Min. current alarm value of slave2"
    ::= { slave2OutputCurrentMin 34}
	
slave2OutputCurrentMinThirtyfive OBJECT-TYPE
    SYNTAX      DisplayString
    MAX-ACCESS  read-write
    STATUS      current
    DESCRIPTION
	"The second output Min. current alarm value of slave2"
    ::= { slave2OutputCurrentMin 35}
	
slave2OutputCurrentMinThirtysix OBJECT-TYPE
    SYNTAX      DisplayString
    MAX-ACCESS  read-write
    STATUS      current
    DESCRIPTION
	"The second output Min. current alarm value of slave2"
    ::= { slave2OutputCurrentMin 36}
	
slave2OutputCurrentMinThirtyseven OBJECT-TYPE
    SYNTAX      DisplayString
    MAX-ACCESS  read-write
    STATUS      current
    DESCRIPTION
	"The second output Min. current alarm value of slave2"
    ::= { slave2OutputCurrentMin 37}
	
slave2OutputCurrentMinThirtyeight OBJECT-TYPE
    SYNTAX      DisplayString
    MAX-ACCESS  read-write
    STATUS      current
    DESCRIPTION
	"The second output Min. current alarm value of slave2"
    ::= { slave2OutputCurrentMin 38}
	
slave2OutputCurrentMinThirtynine OBJECT-TYPE
    SYNTAX      DisplayString
    MAX-ACCESS  read-write
    STATUS      current
    DESCRIPTION
	"The second output Min. current alarm value of slave2"
    ::= { slave2OutputCurrentMin 39}
	
slave2OutputCurrentMinFourty OBJECT-TYPE
    SYNTAX      DisplayString
    MAX-ACCESS  read-write
    STATUS      current
    DESCRIPTION
	"The second output Min. current alarm value of slave2"
    ::= { slave2OutputCurrentMin 40}
	
slave2OutputCurrentMinFourtyone OBJECT-TYPE
    SYNTAX      DisplayString
    MAX-ACCESS  read-write
    STATUS      current
    DESCRIPTION
	"The second output Min. current alarm value of slave2"
    ::= { slave2OutputCurrentMin 41}
	
slave2OutputCurrentMinFourtytwo OBJECT-TYPE
    SYNTAX      DisplayString
    MAX-ACCESS  read-write
    STATUS      current
    DESCRIPTION
	"The second output Min. current alarm value of slave2"
    ::= { slave2OutputCurrentMin 42}


------------------------slave2 output current Min critical----------------			
slave2OutputCurrentMinCritical OBJECT IDENTIFIER ::= { slave2OutputCurrent 3}	

slave2OutputCurrentMinCriticalOne OBJECT-TYPE
    SYNTAX      DisplayString
    MAX-ACCESS  read-write
    STATUS      current
    DESCRIPTION
	"The first output Min. current warning value of slave2"
    ::= { slave2OutputCurrentMinCritical 1}

slave2OutputCurrentMinCriticalTwo OBJECT-TYPE
    SYNTAX      DisplayString
    MAX-ACCESS  read-write
    STATUS      current
    DESCRIPTION
	"The second output Min. current warning value of slave2"
    ::= { slave2OutputCurrentMinCritical 2}

slave2OutputCurrentMinCriticalThree OBJECT-TYPE
    SYNTAX      DisplayString
    MAX-ACCESS  read-write
    STATUS      current
    DESCRIPTION
	"The second output Min. current warning value of slave2"
    ::= { slave2OutputCurrentMinCritical 3}

slave2OutputCurrentMinCriticalFour OBJECT-TYPE
    SYNTAX      DisplayString
    MAX-ACCESS  read-write
    STATUS      current
    DESCRIPTION
	"The second output Min. current warning value of slave2"
    ::= { slave2OutputCurrentMinCritical 4}

slave2OutputCurrentMinCriticalFive OBJECT-TYPE
    SYNTAX      DisplayString
    MAX-ACCESS  read-write
    STATUS      current
    DESCRIPTION
	"The second output Min. current warning value of slave2"
    ::= { slave2OutputCurrentMinCritical 5}

slave2OutputCurrentMinCriticalSix OBJECT-TYPE
    SYNTAX      DisplayString
    MAX-ACCESS  read-write
    STATUS      current
    DESCRIPTION
	"The second output Min. current warning value of slave2"
    ::= { slave2OutputCurrentMinCritical 6}

slave2OutputCurrentMinCriticalSeven OBJECT-TYPE
    SYNTAX      DisplayString
    MAX-ACCESS  read-write
    STATUS      current
    DESCRIPTION
	"The second output Min. current warning value of slave2"
    ::= { slave2OutputCurrentMinCritical 7}

slave2OutputCurrentMinCriticalEight OBJECT-TYPE
    SYNTAX      DisplayString
    MAX-ACCESS  read-write
    STATUS      current
    DESCRIPTION
	"The second output Min. current warning value of slave2"
    ::= { slave2OutputCurrentMinCritical 8}

slave2OutputCurrentMinCriticalNine OBJECT-TYPE
    SYNTAX      DisplayString
    MAX-ACCESS  read-write
    STATUS      current
    DESCRIPTION
	"The second output Min. current warning value of slave2"
    ::= { slave2OutputCurrentMinCritical 9}

slave2OutputCurrentMinCriticalTen OBJECT-TYPE
    SYNTAX      DisplayString
    MAX-ACCESS  read-write
    STATUS      current
    DESCRIPTION
	"The second output Min. current warning value of slave2"
    ::= { slave2OutputCurrentMinCritical 10}

slave2OutputCurrentMinCriticalEleven OBJECT-TYPE
    SYNTAX      DisplayString
    MAX-ACCESS  read-write
    STATUS      current
    DESCRIPTION
	"The second output Min. current warning value of slave2"
    ::= { slave2OutputCurrentMinCritical 11}

slave2OutputCurrentMinCriticalTwel OBJECT-TYPE
    SYNTAX      DisplayString
    MAX-ACCESS  read-write
    STATUS      current
    DESCRIPTION
	"The second output Min. current warning value of slave2"
    ::= { slave2OutputCurrentMinCritical 12}

slave2OutputCurrentMinCriticalThirteen OBJECT-TYPE
    SYNTAX      DisplayString
    MAX-ACCESS  read-write
    STATUS      current
    DESCRIPTION
	"The second output Min. current warning value of slave2"
    ::= { slave2OutputCurrentMinCritical 13}

slave2OutputCurrentMinCriticalFourteen OBJECT-TYPE
    SYNTAX      DisplayString
    MAX-ACCESS  read-write
    STATUS      current
    DESCRIPTION
	"The second output Min. current warning value of slave2"
    ::= { slave2OutputCurrentMinCritical 14}

slave2OutputCurrentMinCriticalFifteen OBJECT-TYPE
    SYNTAX      DisplayString
    MAX-ACCESS  read-write
    STATUS      current
    DESCRIPTION
	"The second output Min. current warning value of slave2"
    ::= { slave2OutputCurrentMinCritical 15}

slave2OutputCurrentMinCriticalSixteen OBJECT-TYPE
    SYNTAX      DisplayString
    MAX-ACCESS  read-write
    STATUS      current
    DESCRIPTION
	"The second output Min. current warning value of slave2"
    ::= { slave2OutputCurrentMinCritical 16}

slave2OutputCurrentMinCriticalSeventeen OBJECT-TYPE
    SYNTAX      DisplayString
    MAX-ACCESS  read-write
    STATUS      current
    DESCRIPTION
	"The second output Min. current warning value of slave2"
    ::= { slave2OutputCurrentMinCritical 17}

slave2OutputCurrentMinCriticalEighteen OBJECT-TYPE
    SYNTAX      DisplayString
    MAX-ACCESS  read-write
    STATUS      current
    DESCRIPTION
	"The second output Min. current warning value of slave2"
    ::= { slave2OutputCurrentMinCritical 18}
	
slave2OutputCurrentMinCriticalNineteen OBJECT-TYPE
    SYNTAX      DisplayString
    MAX-ACCESS  read-write
    STATUS      current
    DESCRIPTION
	"The second output Min. current warning value of slave2"
    ::= { slave2OutputCurrentMinCritical 19}
	
slave2OutputCurrentMinCriticaltwenty OBJECT-TYPE
    SYNTAX      DisplayString
    MAX-ACCESS  read-write
    STATUS      current
    DESCRIPTION
	"The second output Min. current warning value of slave2"
    ::= { slave2OutputCurrentMinCritical 20}
	
slave2OutputCurrentMinCriticalTwentyone OBJECT-TYPE
    SYNTAX      DisplayString
    MAX-ACCESS  read-write
    STATUS      current
    DESCRIPTION
	"The second output Min. current warning value of slave2"
    ::= { slave2OutputCurrentMinCritical 21}
	
slave2OutputCurrentMinCriticalTwentyonetwo OBJECT-TYPE
    SYNTAX      DisplayString
    MAX-ACCESS  read-write
    STATUS      current
    DESCRIPTION
	"The second output Min. current warning value of slave2"
    ::= { slave2OutputCurrentMinCritical 22}
	
slave2OutputCurrentMinCriticalTwentythree OBJECT-TYPE
    SYNTAX      DisplayString
    MAX-ACCESS  read-write
    STATUS      current
    DESCRIPTION
	"The second output Min. current warning value of slave2"
    ::= { slave2OutputCurrentMinCritical 23}
	
slave2OutputCurrentMinCriticalTwentyfour OBJECT-TYPE
    SYNTAX      DisplayString
    MAX-ACCESS  read-write
    STATUS      current
    DESCRIPTION
	"The second output Min. current warning value of slave2"
    ::= { slave2OutputCurrentMinCritical 24}
	
slave2OutputCurrentMinCriticalTwentyfive OBJECT-TYPE
    SYNTAX      DisplayString
    MAX-ACCESS  read-write
    STATUS      current
    DESCRIPTION
	"The second output Min. current warning value of slave2"
    ::= { slave2OutputCurrentMinCritical 25}
	
slave2OutputCurrentMinCriticalTwentysix OBJECT-TYPE
    SYNTAX      DisplayString
    MAX-ACCESS  read-write
    STATUS      current
    DESCRIPTION
	"The second output Min. current warning value of slave2"
    ::= { slave2OutputCurrentMinCritical 26}
	
slave2OutputCurrentMinCriticalTwentyseven OBJECT-TYPE
    SYNTAX      DisplayString
    MAX-ACCESS  read-write
    STATUS      current
    DESCRIPTION
	"The second output Min. current warning value of slave2"
    ::= { slave2OutputCurrentMinCritical 27}
	
slave2OutputCurrentMinCriticalTwentyeight OBJECT-TYPE
    SYNTAX      DisplayString
    MAX-ACCESS  read-write
    STATUS      current
    DESCRIPTION
	"The second output Min. current warning value of slave2"
    ::= { slave2OutputCurrentMinCritical 28}	
slave2OutputCurrentMinCriticalTwentynine OBJECT-TYPE
    SYNTAX      DisplayString
    MAX-ACCESS  read-write
    STATUS      current
    DESCRIPTION
	"The second output Min. current warning value of slave2"
    ::= { slave2OutputCurrentMinCritical 29}
	
slave2OutputCurrentMinCriticalThirty OBJECT-TYPE
    SYNTAX      DisplayString
    MAX-ACCESS  read-write
    STATUS      current
    DESCRIPTION
	"The second output Min. current warning value of slave2"
    ::= { slave2OutputCurrentMinCritical 30}
	
slave2OutputCurrentMinCriticalThirtyone OBJECT-TYPE
    SYNTAX      DisplayString
    MAX-ACCESS  read-write
    STATUS      current
    DESCRIPTION
	"The second output Min. current warning value of slave2"
    ::= { slave2OutputCurrentMinCritical 31}
	
slave2OutputCurrentMinCriticalThirtytwo OBJECT-TYPE
    SYNTAX      DisplayString
    MAX-ACCESS  read-write
    STATUS      current
    DESCRIPTION
	"The second output Min. current warning value of slave2"
    ::= { slave2OutputCurrentMinCritical 32}
	
slave2OutputCurrentMinCriticalThirtythree OBJECT-TYPE
    SYNTAX      DisplayString
    MAX-ACCESS  read-write
    STATUS      current
    DESCRIPTION
	"The second output Min. current warning value of slave2"
    ::= { slave2OutputCurrentMinCritical 33}
	
slave2OutputCurrentMinCriticalThirtyfour OBJECT-TYPE
    SYNTAX      DisplayString
    MAX-ACCESS  read-write
    STATUS      current
    DESCRIPTION
	"The second output Min. current warning value of slave2"
    ::= { slave2OutputCurrentMinCritical 34}
	
slave2OutputCurrentMinCriticalThirtyfive OBJECT-TYPE
    SYNTAX      DisplayString
    MAX-ACCESS  read-write
    STATUS      current
    DESCRIPTION
	"The second output Min. current warning value of slave2"
    ::= { slave2OutputCurrentMinCritical 35}
	
slave2OutputCurrentMinCriticalThirtysix OBJECT-TYPE
    SYNTAX      DisplayString
    MAX-ACCESS  read-write
    STATUS      current
    DESCRIPTION
	"The second output Min. current warning value of slave2"
    ::= { slave2OutputCurrentMinCritical 36}
	
slave2OutputCurrentMinCriticalThirtyseven OBJECT-TYPE
    SYNTAX      DisplayString
    MAX-ACCESS  read-write
    STATUS      current
    DESCRIPTION
	"The second output Min. current warning value of slave2"
    ::= { slave2OutputCurrentMinCritical 37}
	
slave2OutputCurrentMinCriticalThirtyeight OBJECT-TYPE
    SYNTAX      DisplayString
    MAX-ACCESS  read-write
    STATUS      current
    DESCRIPTION
	"The second output Min. current warning value of slave2"
    ::= { slave2OutputCurrentMinCritical 38}
	
slave2OutputCurrentMinCriticalThirtynine OBJECT-TYPE
    SYNTAX      DisplayString
    MAX-ACCESS  read-write
    STATUS      current
    DESCRIPTION
	"The second output Min. current warning value of slave2"
    ::= { slave2OutputCurrentMinCritical 39}
	
slave2OutputCurrentMinCriticalFourty OBJECT-TYPE
    SYNTAX      DisplayString
    MAX-ACCESS  read-write
    STATUS      current
    DESCRIPTION
	"The second output Min. current warning value of slave2"
    ::= { slave2OutputCurrentMinCritical 40}
	
slave2OutputCurrentMinCriticalFourtyone OBJECT-TYPE
    SYNTAX      DisplayString
    MAX-ACCESS  read-write
    STATUS      current
    DESCRIPTION
	"The second output Min. current warning value of slave2"
    ::= { slave2OutputCurrentMinCritical 41}
	
slave2OutputCurrentMinCriticalFourtytwo OBJECT-TYPE
    SYNTAX      DisplayString
    MAX-ACCESS  read-write
    STATUS      current
    DESCRIPTION
	"The second output Min. current warning value of slave2"
    ::= { slave2OutputCurrentMinCritical 42}
	
	
------------------------slave2 output current Max critical----------------			
slave2OutputCurrentMaxCritical OBJECT IDENTIFIER ::= { slave2OutputCurrent 4}	

slave2OutputCurrentMaxCriticalOne OBJECT-TYPE
    SYNTAX      DisplayString
    MAX-ACCESS  read-write
    STATUS      current
    DESCRIPTION
	"The first output Max. current warning value of slave2"
    ::= { slave2OutputCurrentMaxCritical 1}

slave2OutputCurrentMaxCriticalTwo OBJECT-TYPE
    SYNTAX      DisplayString
    MAX-ACCESS  read-write
    STATUS      current
    DESCRIPTION
	"The second output Max. current warning value of slave2"
    ::= { slave2OutputCurrentMaxCritical 2}

slave2OutputCurrentMaxCriticalThree OBJECT-TYPE
    SYNTAX      DisplayString
    MAX-ACCESS  read-write
    STATUS      current
    DESCRIPTION
	"The second output Max. current warning value of slave2"
    ::= { slave2OutputCurrentMaxCritical 3}

slave2OutputCurrentMaxCriticalFour OBJECT-TYPE
    SYNTAX      DisplayString
    MAX-ACCESS  read-write
    STATUS      current
    DESCRIPTION
	"The second output Max. current warning value of slave2"
    ::= { slave2OutputCurrentMaxCritical 4}

slave2OutputCurrentMaxCriticalFive OBJECT-TYPE
    SYNTAX      DisplayString
    MAX-ACCESS  read-write
    STATUS      current
    DESCRIPTION
	"The second output Max. current warning value of slave2"
    ::= { slave2OutputCurrentMaxCritical 5}

slave2OutputCurrentMaxCriticalSix OBJECT-TYPE
    SYNTAX      DisplayString
    MAX-ACCESS  read-write
    STATUS      current
    DESCRIPTION
	"The second output Max. current warning value of slave2"
    ::= { slave2OutputCurrentMaxCritical 6}

slave2OutputCurrentMaxCriticalSeven OBJECT-TYPE
    SYNTAX      DisplayString
    MAX-ACCESS  read-write
    STATUS      current
    DESCRIPTION
	"The second output Max. current warning value of slave2"
    ::= { slave2OutputCurrentMaxCritical 7}

slave2OutputCurrentMaxCriticalEight OBJECT-TYPE
    SYNTAX      DisplayString
    MAX-ACCESS  read-write
    STATUS      current
    DESCRIPTION
	"The second output Max. current warning value of slave2"
    ::= { slave2OutputCurrentMaxCritical 8}

slave2OutputCurrentMaxCriticalNine OBJECT-TYPE
    SYNTAX      DisplayString
    MAX-ACCESS  read-write
    STATUS      current
    DESCRIPTION
	"The second output Max. current warning value of slave2"
    ::= { slave2OutputCurrentMaxCritical 9}

slave2OutputCurrentMaxCriticalTen OBJECT-TYPE
    SYNTAX      DisplayString
    MAX-ACCESS  read-write
    STATUS      current
    DESCRIPTION
	"The second output Max. current warning value of slave2"
    ::= { slave2OutputCurrentMaxCritical 10}

slave2OutputCurrentMaxCriticalEleven OBJECT-TYPE
    SYNTAX      DisplayString
    MAX-ACCESS  read-write
    STATUS      current
    DESCRIPTION
	"The second output Max. current warning value of slave2"
    ::= { slave2OutputCurrentMaxCritical 11}

slave2OutputCurrentMaxCriticalTwel OBJECT-TYPE
    SYNTAX      DisplayString
    MAX-ACCESS  read-write
    STATUS      current
    DESCRIPTION
	"The second output Max. current warning value of slave2"
    ::= { slave2OutputCurrentMaxCritical 12}

slave2OutputCurrentMaxCriticalThirteen OBJECT-TYPE
    SYNTAX      DisplayString
    MAX-ACCESS  read-write
    STATUS      current
    DESCRIPTION
	"The second output Max. current warning value of slave2"
    ::= { slave2OutputCurrentMaxCritical 13}

slave2OutputCurrentMaxCriticalFourteen OBJECT-TYPE
    SYNTAX      DisplayString
    MAX-ACCESS  read-write
    STATUS      current
    DESCRIPTION
	"The second output Max. current warning value of slave2"
    ::= { slave2OutputCurrentMaxCritical 14}

slave2OutputCurrentMaxCriticalFifteen OBJECT-TYPE
    SYNTAX      DisplayString
    MAX-ACCESS  read-write
    STATUS      current
    DESCRIPTION
	"The second output Max. current warning value of slave2"
    ::= { slave2OutputCurrentMaxCritical 15}

slave2OutputCurrentMaxCriticalSixteen OBJECT-TYPE
    SYNTAX      DisplayString
    MAX-ACCESS  read-write
    STATUS      current
    DESCRIPTION
	"The second output Max. current warning value of slave2"
    ::= { slave2OutputCurrentMaxCritical 16}

slave2OutputCurrentMaxCriticalSeventeen OBJECT-TYPE
    SYNTAX      DisplayString
    MAX-ACCESS  read-write
    STATUS      current
    DESCRIPTION
	"The second output Max. current warning value of slave2"
    ::= { slave2OutputCurrentMaxCritical 17}

slave2OutputCurrentMaxCriticalEighteen OBJECT-TYPE
    SYNTAX      DisplayString
    MAX-ACCESS  read-write
    STATUS      current
    DESCRIPTION
	"The second output Max. current warning value of slave2"
    ::= { slave2OutputCurrentMaxCritical 18}
	
slave2OutputCurrentMaxCriticalNineteen OBJECT-TYPE
    SYNTAX      DisplayString
    MAX-ACCESS  read-write
    STATUS      current
    DESCRIPTION
	"The second output Max. current warning value of slave2"
    ::= { slave2OutputCurrentMaxCritical 19}
	
slave2OutputCurrentMaxCriticaltwenty OBJECT-TYPE
    SYNTAX      DisplayString
    MAX-ACCESS  read-write
    STATUS      current
    DESCRIPTION
	"The second output Max. current warning value of slave2"
    ::= { slave2OutputCurrentMaxCritical 20}
	
slave2OutputCurrentMaxCriticalTwentyone OBJECT-TYPE
    SYNTAX      DisplayString
    MAX-ACCESS  read-write
    STATUS      current
    DESCRIPTION
	"The second output Max. current warning value of slave2"
    ::= { slave2OutputCurrentMaxCritical 21}
	
slave2OutputCurrentMaxCriticalTwentyonetwo OBJECT-TYPE
    SYNTAX      DisplayString
    MAX-ACCESS  read-write
    STATUS      current
    DESCRIPTION
	"The second output Max. current warning value of slave2"
    ::= { slave2OutputCurrentMaxCritical 22}
	
slave2OutputCurrentMaxCriticalTwentythree OBJECT-TYPE
    SYNTAX      DisplayString
    MAX-ACCESS  read-write
    STATUS      current
    DESCRIPTION
	"The second output Max. current warning value of slave2"
    ::= { slave2OutputCurrentMaxCritical 23}
	
slave2OutputCurrentMaxCriticalTwentyfour OBJECT-TYPE
    SYNTAX      DisplayString
    MAX-ACCESS  read-write
    STATUS      current
    DESCRIPTION
	"The second output Max. current warning value of slave2"
    ::= { slave2OutputCurrentMaxCritical 24}
	
slave2OutputCurrentMaxCriticalTwentyfive OBJECT-TYPE
    SYNTAX      DisplayString
    MAX-ACCESS  read-write
    STATUS      current
    DESCRIPTION
	"The second output Max. current warning value of slave2"
    ::= { slave2OutputCurrentMaxCritical 25}
	
slave2OutputCurrentMaxCriticalTwentysix OBJECT-TYPE
    SYNTAX      DisplayString
    MAX-ACCESS  read-write
    STATUS      current
    DESCRIPTION
	"The second output Max. current warning value of slave2"
    ::= { slave2OutputCurrentMaxCritical 26}
	
slave2OutputCurrentMaxCriticalTwentyseven OBJECT-TYPE
    SYNTAX      DisplayString
    MAX-ACCESS  read-write
    STATUS      current
    DESCRIPTION
	"The second output Max. current warning value of slave2"
    ::= { slave2OutputCurrentMaxCritical 27}
	
slave2OutputCurrentMaxCriticalTwentyeight OBJECT-TYPE
    SYNTAX      DisplayString
    MAX-ACCESS  read-write
    STATUS      current
    DESCRIPTION
	"The second output Max. current warning value of slave2"
    ::= { slave2OutputCurrentMaxCritical 28}	
slave2OutputCurrentMaxCriticalTwentynine OBJECT-TYPE
    SYNTAX      DisplayString
    MAX-ACCESS  read-write
    STATUS      current
    DESCRIPTION
	"The second output Max. current warning value of slave2"
    ::= { slave2OutputCurrentMaxCritical 29}
	
slave2OutputCurrentMaxCriticalThirty OBJECT-TYPE
    SYNTAX      DisplayString
    MAX-ACCESS  read-write
    STATUS      current
    DESCRIPTION
	"The second output Max. current warning value of slave2"
    ::= { slave2OutputCurrentMaxCritical 30}
	
slave2OutputCurrentMaxCriticalThirtyone OBJECT-TYPE
    SYNTAX      DisplayString
    MAX-ACCESS  read-write
    STATUS      current
    DESCRIPTION
	"The second output Max. current warning value of slave2"
    ::= { slave2OutputCurrentMaxCritical 31}
	
slave2OutputCurrentMaxCriticalThirtytwo OBJECT-TYPE
    SYNTAX      DisplayString
    MAX-ACCESS  read-write
    STATUS      current
    DESCRIPTION
	"The second output Max. current warning value of slave2"
    ::= { slave2OutputCurrentMaxCritical 32}
	
slave2OutputCurrentMaxCriticalThirtythree OBJECT-TYPE
    SYNTAX      DisplayString
    MAX-ACCESS  read-write
    STATUS      current
    DESCRIPTION
	"The second output Max. current warning value of slave2"
    ::= { slave2OutputCurrentMaxCritical 33}
	
slave2OutputCurrentMaxCriticalThirtyfour OBJECT-TYPE
    SYNTAX      DisplayString
    MAX-ACCESS  read-write
    STATUS      current
    DESCRIPTION
	"The second output Max. current warning value of slave2"
    ::= { slave2OutputCurrentMaxCritical 34}
	
slave2OutputCurrentMaxCriticalThirtyfive OBJECT-TYPE
    SYNTAX      DisplayString
    MAX-ACCESS  read-write
    STATUS      current
    DESCRIPTION
	"The second output Max. current warning value of slave2"
    ::= { slave2OutputCurrentMaxCritical 35}
	
slave2OutputCurrentMaxCriticalThirtysix OBJECT-TYPE
    SYNTAX      DisplayString
    MAX-ACCESS  read-write
    STATUS      current
    DESCRIPTION
	"The second output Max. current warning value of slave2"
    ::= { slave2OutputCurrentMaxCritical 36}
	
slave2OutputCurrentMaxCriticalThirtyseven OBJECT-TYPE
    SYNTAX      DisplayString
    MAX-ACCESS  read-write
    STATUS      current
    DESCRIPTION
	"The second output Max. current warning value of slave2"
    ::= { slave2OutputCurrentMaxCritical 37}
	
slave2OutputCurrentMaxCriticalThirtyeight OBJECT-TYPE
    SYNTAX      DisplayString
    MAX-ACCESS  read-write
    STATUS      current
    DESCRIPTION
	"The second output Max. current warning value of slave2"
    ::= { slave2OutputCurrentMaxCritical 38}
	
slave2OutputCurrentMaxCriticalThirtynine OBJECT-TYPE
    SYNTAX      DisplayString
    MAX-ACCESS  read-write
    STATUS      current
    DESCRIPTION
	"The second output Max. current warning value of slave2"
    ::= { slave2OutputCurrentMaxCritical 39}
	
slave2OutputCurrentMaxCriticalFourty OBJECT-TYPE
    SYNTAX      DisplayString
    MAX-ACCESS  read-write
    STATUS      current
    DESCRIPTION
	"The second output Max. current warning value of slave2"
    ::= { slave2OutputCurrentMaxCritical 40}
	
slave2OutputCurrentMaxCriticalFourtyone OBJECT-TYPE
    SYNTAX      DisplayString
    MAX-ACCESS  read-write
    STATUS      current
    DESCRIPTION
	"The second output Max. current warning value of slave2"
    ::= { slave2OutputCurrentMaxCritical 41}
	
slave2OutputCurrentMaxCriticalFourtytwo OBJECT-TYPE
    SYNTAX      DisplayString
    MAX-ACCESS  read-write
    STATUS      current
    DESCRIPTION
	"The second output Max. current warning value of slave2"
    ::= { slave2OutputCurrentMaxCritical 42}
	
	
------------------------slave2 output current Max----------------			
slave2OutputCurrentMax OBJECT IDENTIFIER ::= { slave2OutputCurrent 5}
	
slave2OutputCurrentMaxOne OBJECT-TYPE
    SYNTAX      DisplayString
    MAX-ACCESS  read-write
    STATUS      current
    DESCRIPTION
	"The first output Max. current alarm value of slave2"
    ::= { slave2OutputCurrentMax 1}

slave2OutputCurrentMaxTwo OBJECT-TYPE
    SYNTAX      DisplayString
    MAX-ACCESS  read-write
    STATUS      current
    DESCRIPTION
	"The second output Max. current alarm value of slave2"
    ::= { slave2OutputCurrentMax 2}

slave2OutputCurrentMaxThree OBJECT-TYPE
    SYNTAX      DisplayString
    MAX-ACCESS  read-write
    STATUS      current
    DESCRIPTION
	"The second output Max. current alarm value of slave2"
    ::= { slave2OutputCurrentMax 3}

slave2OutputCurrentMaxFour OBJECT-TYPE
    SYNTAX      DisplayString
    MAX-ACCESS  read-write
    STATUS      current
    DESCRIPTION
	"The second output Max. current alarm value of slave2"
    ::= { slave2OutputCurrentMax 4}

slave2OutputCurrentMaxFive OBJECT-TYPE
    SYNTAX      DisplayString
    MAX-ACCESS  read-write
    STATUS      current
    DESCRIPTION
	"The second output Max. current alarm value of slave2"
    ::= { slave2OutputCurrentMax 5}

slave2OutputCurrentMaxSix OBJECT-TYPE
    SYNTAX      DisplayString
    MAX-ACCESS  read-write
    STATUS      current
    DESCRIPTION
	"The second output Max. current alarm value of slave2"
    ::= { slave2OutputCurrentMax 6}

slave2OutputCurrentMaxSeven OBJECT-TYPE
    SYNTAX      DisplayString
    MAX-ACCESS  read-write
    STATUS      current
    DESCRIPTION
	"The second output Max. current alarm value of slave2"
    ::= { slave2OutputCurrentMax 7}

slave2OutputCurrentMaxEight OBJECT-TYPE
    SYNTAX      DisplayString
    MAX-ACCESS  read-write
    STATUS      current
    DESCRIPTION
	"The second output Max. current alarm value of slave2"
    ::= { slave2OutputCurrentMax 8}

slave2OutputCurrentMaxNine OBJECT-TYPE
    SYNTAX      DisplayString
    MAX-ACCESS  read-write
    STATUS      current
    DESCRIPTION
	"The second output Max. current alarm value of slave2"
    ::= { slave2OutputCurrentMax 9}

slave2OutputCurrentMaxTen OBJECT-TYPE
    SYNTAX      DisplayString
    MAX-ACCESS  read-write
    STATUS      current
    DESCRIPTION
	"The second output Max. current alarm value of slave2"
    ::= { slave2OutputCurrentMax 10}

slave2OutputCurrentMaxEleven OBJECT-TYPE
    SYNTAX      DisplayString
    MAX-ACCESS  read-write
    STATUS      current
    DESCRIPTION
	"The second output Max. current alarm value of slave2"
    ::= { slave2OutputCurrentMax 11}

slave2OutputCurrentMaxTwel OBJECT-TYPE
    SYNTAX      DisplayString
    MAX-ACCESS  read-write
    STATUS      current
    DESCRIPTION
	"The second output Max. current alarm value of slave2"
    ::= { slave2OutputCurrentMax 12}

slave2OutputCurrentMaxThirteen OBJECT-TYPE
    SYNTAX      DisplayString
    MAX-ACCESS  read-write
    STATUS      current
    DESCRIPTION
	"The second output Max. current alarm value of slave2"
    ::= { slave2OutputCurrentMax 13}

slave2OutputCurrentMaxFourteen OBJECT-TYPE
    SYNTAX      DisplayString
    MAX-ACCESS  read-write
    STATUS      current
    DESCRIPTION
	"The second output Max. current alarm value of slave2"
    ::= { slave2OutputCurrentMax 14}

slave2OutputCurrentMaxFifteen OBJECT-TYPE
    SYNTAX      DisplayString
    MAX-ACCESS  read-write
    STATUS      current
    DESCRIPTION
	"The second output Max. current alarm value of slave2"
    ::= { slave2OutputCurrentMax 15}

slave2OutputCurrentMaxSixteen OBJECT-TYPE
    SYNTAX      DisplayString
    MAX-ACCESS  read-write
    STATUS      current
    DESCRIPTION
	"The second output Max. current alarm value of slave2"
    ::= { slave2OutputCurrentMax 16}

slave2OutputCurrentMaxSeventeen OBJECT-TYPE
    SYNTAX      DisplayString
    MAX-ACCESS  read-write
    STATUS      current
    DESCRIPTION
	"The second output Max. current alarm value of slave2"
    ::= { slave2OutputCurrentMax 17}

slave2OutputCurrentMaxEighteen OBJECT-TYPE
    SYNTAX      DisplayString
    MAX-ACCESS  read-write
    STATUS      current
    DESCRIPTION
	"The second output Max. current alarm value of slave2"
    ::= { slave2OutputCurrentMax 18}
	
slave2OutputCurrentMaxNineteen OBJECT-TYPE
    SYNTAX      DisplayString
    MAX-ACCESS  read-write
    STATUS      current
    DESCRIPTION
	"The second output Max. current alarm value of slave2"
    ::= { slave2OutputCurrentMax 19}
	
slave2OutputCurrentMaxtwenty OBJECT-TYPE
    SYNTAX      DisplayString
    MAX-ACCESS  read-write
    STATUS      current
    DESCRIPTION
	"The second output Max. current alarm value of slave2"
    ::= { slave2OutputCurrentMax 20}
	
slave2OutputCurrentMaxTwentyone OBJECT-TYPE
    SYNTAX      DisplayString
    MAX-ACCESS  read-write
    STATUS      current
    DESCRIPTION
	"The second output Max. current alarm value of slave2"
    ::= { slave2OutputCurrentMax 21}
	
slave2OutputCurrentMaxTwentyonetwo OBJECT-TYPE
    SYNTAX      DisplayString
    MAX-ACCESS  read-write
    STATUS      current
    DESCRIPTION
	"The second output Max. current alarm value of slave2"
    ::= { slave2OutputCurrentMax 22}
	
slave2OutputCurrentMaxTwentythree OBJECT-TYPE
    SYNTAX      DisplayString
    MAX-ACCESS  read-write
    STATUS      current
    DESCRIPTION
	"The second output Max. current alarm value of slave2"
    ::= { slave2OutputCurrentMax 23}
	
slave2OutputCurrentMaxTwentyfour OBJECT-TYPE
    SYNTAX      DisplayString
    MAX-ACCESS  read-write
    STATUS      current
    DESCRIPTION
	"The second output Max. current alarm value of slave2"
    ::= { slave2OutputCurrentMax 24}
	
slave2OutputCurrentMaxTwentyfive OBJECT-TYPE
    SYNTAX      DisplayString
    MAX-ACCESS  read-write
    STATUS      current
    DESCRIPTION
	"The second output Max. current alarm value of slave2"
    ::= { slave2OutputCurrentMax 25}
	
slave2OutputCurrentMaxTwentysix OBJECT-TYPE
    SYNTAX      DisplayString
    MAX-ACCESS  read-write
    STATUS      current
    DESCRIPTION
	"The second output Max. current alarm value of slave2"
    ::= { slave2OutputCurrentMax 26}
	
slave2OutputCurrentMaxTwentyseven OBJECT-TYPE
    SYNTAX      DisplayString
    MAX-ACCESS  read-write
    STATUS      current
    DESCRIPTION
	"The second output Max. current alarm value of slave2"
    ::= { slave2OutputCurrentMax 27}
	
slave2OutputCurrentMaxTwentyeight OBJECT-TYPE
    SYNTAX      DisplayString
    MAX-ACCESS  read-write
    STATUS      current
    DESCRIPTION
	"The second output Max. current alarm value of slave2"
    ::= { slave2OutputCurrentMax 28}	
slave2OutputCurrentMaxTwentynine OBJECT-TYPE
    SYNTAX      DisplayString
    MAX-ACCESS  read-write
    STATUS      current
    DESCRIPTION
	"The second output Max. current alarm value of slave2"
    ::= { slave2OutputCurrentMax 29}
	
slave2OutputCurrentMaxThirty OBJECT-TYPE
    SYNTAX      DisplayString
    MAX-ACCESS  read-write
    STATUS      current
    DESCRIPTION
	"The second output Max. current alarm value of slave2"
    ::= { slave2OutputCurrentMax 30}
	
slave2OutputCurrentMaxThirtyone OBJECT-TYPE
    SYNTAX      DisplayString
    MAX-ACCESS  read-write
    STATUS      current
    DESCRIPTION
	"The second output Max. current alarm value of slave2"
    ::= { slave2OutputCurrentMax 31}
	
slave2OutputCurrentMaxThirtytwo OBJECT-TYPE
    SYNTAX      DisplayString
    MAX-ACCESS  read-write
    STATUS      current
    DESCRIPTION
	"The second output Max. current alarm value of slave2"
    ::= { slave2OutputCurrentMax 32}
	
slave2OutputCurrentMaxThirtythree OBJECT-TYPE
    SYNTAX      DisplayString
    MAX-ACCESS  read-write
    STATUS      current
    DESCRIPTION
	"The second output Max. current alarm value of slave2"
    ::= { slave2OutputCurrentMax 33}
	
slave2OutputCurrentMaxThirtyfour OBJECT-TYPE
    SYNTAX      DisplayString
    MAX-ACCESS  read-write
    STATUS      current
    DESCRIPTION
	"The second output Max. current alarm value of slave2"
    ::= { slave2OutputCurrentMax 34}
	
slave2OutputCurrentMaxThirtyfive OBJECT-TYPE
    SYNTAX      DisplayString
    MAX-ACCESS  read-write
    STATUS      current
    DESCRIPTION
	"The second output Max. current alarm value of slave2"
    ::= { slave2OutputCurrentMax 35}
	
slave2OutputCurrentMaxThirtysix OBJECT-TYPE
    SYNTAX      DisplayString
    MAX-ACCESS  read-write
    STATUS      current
    DESCRIPTION
	"The second output Max. current alarm value of slave2"
    ::= { slave2OutputCurrentMax 36}
	
slave2OutputCurrentMaxThirtyseven OBJECT-TYPE
    SYNTAX      DisplayString
    MAX-ACCESS  read-write
    STATUS      current
    DESCRIPTION
	"The second output Max. current alarm value of slave2"
    ::= { slave2OutputCurrentMax 37}
	
slave2OutputCurrentMaxThirtyeight OBJECT-TYPE
    SYNTAX      DisplayString
    MAX-ACCESS  read-write
    STATUS      current
    DESCRIPTION
	"The second output Max. current alarm value of slave2"
    ::= { slave2OutputCurrentMax 38}
	
slave2OutputCurrentMaxThirtynine OBJECT-TYPE
    SYNTAX      DisplayString
    MAX-ACCESS  read-write
    STATUS      current
    DESCRIPTION
	"The second output Max. current alarm value of slave2"
    ::= { slave2OutputCurrentMax 39}
	
slave2OutputCurrentMaxFourty OBJECT-TYPE
    SYNTAX      DisplayString
    MAX-ACCESS  read-write
    STATUS      current
    DESCRIPTION
	"The second output Max. current alarm value of slave2"
    ::= { slave2OutputCurrentMax 40}
	
slave2OutputCurrentMaxFourtyone OBJECT-TYPE
    SYNTAX      DisplayString
    MAX-ACCESS  read-write
    STATUS      current
    DESCRIPTION
	"The second output Max. current alarm value of slave2"
    ::= { slave2OutputCurrentMax 41}
	
slave2OutputCurrentMaxFourtytwo OBJECT-TYPE
    SYNTAX      DisplayString
    MAX-ACCESS  read-write
    STATUS      current
    DESCRIPTION
	"The second output Max. current alarm value of slave2"
    ::= { slave2OutputCurrentMax 42}
	
	
-------------------------------slave2 output powerfactor------------------------	
slave2OutputPowerfactor OBJECT IDENTIFIER ::= { slave2 9}	

slave2OutputPowerfactorOne OBJECT-TYPE
    SYNTAX      DisplayString
    MAX-ACCESS  read-only
    STATUS      current
    DESCRIPTION
	"The ouput power factor of slave2." 
	::= { slave2OutputPowerfactor 1}

slave2OutputPowerfactorTwo OBJECT-TYPE
    SYNTAX      DisplayString
    MAX-ACCESS  read-only
    STATUS      current
    DESCRIPTION
	"The ouput power factor of slave2." 
	::= { slave2OutputPowerfactor 2}
	
slave2OutputPowerfactorThree OBJECT-TYPE
    SYNTAX      DisplayString
    MAX-ACCESS  read-only
    STATUS      current
    DESCRIPTION
	"The ouput power factor of slave2." 
	::= { slave2OutputPowerfactor 3}
	
slave2OutputPowerfactorFour OBJECT-TYPE
    SYNTAX      DisplayString
    MAX-ACCESS  read-only
    STATUS      current
    DESCRIPTION
	"The ouput power factor of slave2." 
	::= { slave2OutputPowerfactor 4}
		
slave2OutputPowerfactorFive OBJECT-TYPE
    SYNTAX      DisplayString
    MAX-ACCESS  read-only
    STATUS      current
    DESCRIPTION
	"The ouput power factor of slave2." 
	::= { slave2OutputPowerfactor 5}
	
slave2OutputPowerfactorSix OBJECT-TYPE
    SYNTAX      DisplayString
    MAX-ACCESS  read-only
    STATUS      current
    DESCRIPTION
	"The ouput power factor of slave2." 
	::= { slave2OutputPowerfactor 6}
	
slave2OutputPowerfactorSeven OBJECT-TYPE
    SYNTAX      DisplayString
    MAX-ACCESS  read-only
    STATUS      current
    DESCRIPTION
	"The ouput power factor of slave2." 
	::= { slave2OutputPowerfactor 7}	
	
slave2OutputPowerfactorEight OBJECT-TYPE
    SYNTAX      DisplayString
    MAX-ACCESS  read-only
    STATUS      current
    DESCRIPTION
	"The ouput power factor of slave2." 
	::= { slave2OutputPowerfactor 8}
	
slave2OutputPowerfactorNine OBJECT-TYPE
    SYNTAX      DisplayString
    MAX-ACCESS  read-only
    STATUS      current
    DESCRIPTION
	"The ouput power factor of slave2." 
	::= { slave2OutputPowerfactor 9}
		
slave2OutputPowerfactorTen OBJECT-TYPE
    SYNTAX      DisplayString
    MAX-ACCESS  read-only
    STATUS      current
    DESCRIPTION
	"The ouput power factor of slave2." 
	::= { slave2OutputPowerfactor 10}
		
slave2OutputPowerfactorEleven OBJECT-TYPE
    SYNTAX      DisplayString
    MAX-ACCESS  read-only
    STATUS      current
    DESCRIPTION
	"The ouput power factor of slave2." 
	::= { slave2OutputPowerfactor 11}
		
slave2OutputPowerfactorTwel OBJECT-TYPE
    SYNTAX      DisplayString
    MAX-ACCESS  read-only
    STATUS      current
    DESCRIPTION
	"The ouput power factor of slave2." 
	::= { slave2OutputPowerfactor 12}
		
slave2OutputPowerfactorThirteen OBJECT-TYPE
    SYNTAX      DisplayString
    MAX-ACCESS  read-only
    STATUS      current
    DESCRIPTION
	"The ouput power factor of slave2." 
	::= { slave2OutputPowerfactor 13}
		
slave2OutputPowerfactorFourteen OBJECT-TYPE
    SYNTAX      DisplayString
    MAX-ACCESS  read-only
    STATUS      current
    DESCRIPTION
	"The ouput power factor of slave2." 
	::= { slave2OutputPowerfactor 14}
		
slave2OutputPowerfactorFifteen OBJECT-TYPE
    SYNTAX      DisplayString
    MAX-ACCESS  read-only
    STATUS      current
    DESCRIPTION
	"The ouput power factor of slave2." 
	::= { slave2OutputPowerfactor 15}
		
slave2OutputPowerfactorSixteen OBJECT-TYPE
    SYNTAX      DisplayString
    MAX-ACCESS  read-only
    STATUS      current
    DESCRIPTION
	"The ouput power factor of slave2." 
	::= { slave2OutputPowerfactor 16}
		
slave2OutputPowerfactorSeventeen OBJECT-TYPE
    SYNTAX      DisplayString
    MAX-ACCESS  read-only
    STATUS      current
    DESCRIPTION
	"The ouput power factor of slave2." 
	::= { slave2OutputPowerfactor 17}
		
slave2OutputPowerfactorEighteen OBJECT-TYPE
    SYNTAX      DisplayString
    MAX-ACCESS  read-only
    STATUS      current
    DESCRIPTION
	"The ouput power factor of slave2." 
	::= { slave2OutputPowerfactor 18}
		
slave2OutputPowerfactorNineteen OBJECT-TYPE
    SYNTAX      DisplayString
    MAX-ACCESS  read-only
    STATUS      current
    DESCRIPTION
	"The ouput power factor of slave2." 
	::= { slave2OutputPowerfactor 19}
		
slave2OutputPowerfactorTwenty OBJECT-TYPE
    SYNTAX      DisplayString
    MAX-ACCESS  read-only
    STATUS      current
    DESCRIPTION
	"The ouput power factor of slave2." 
	::= { slave2OutputPowerfactor 20}
		
slave2OutputPowerfactorTwentyone OBJECT-TYPE
    SYNTAX      DisplayString
    MAX-ACCESS  read-only
    STATUS      current
    DESCRIPTION
	"The ouput power factor of slave2." 
	::= { slave2OutputPowerfactor 21}
		
slave2OutputPowerfactorTwentytwo OBJECT-TYPE
    SYNTAX      DisplayString
    MAX-ACCESS  read-only
    STATUS      current
    DESCRIPTION
	"The ouput power factor of slave2." 
	::= { slave2OutputPowerfactor 22}
		
slave2OutputPowerfactorTwentythree OBJECT-TYPE
    SYNTAX      DisplayString
    MAX-ACCESS  read-only
    STATUS      current
    DESCRIPTION
	"The ouput power factor of slave2." 
	::= { slave2OutputPowerfactor 23}
		
slave2OutputPowerfactorTwentyfour OBJECT-TYPE
    SYNTAX      DisplayString
    MAX-ACCESS  read-only
    STATUS      current
    DESCRIPTION
	"The ouput power factor of slave2." 
	::= { slave2OutputPowerfactor 24}
		
slave2OutputPowerfactorTwentyfive OBJECT-TYPE
    SYNTAX      DisplayString
    MAX-ACCESS  read-only
    STATUS      current
    DESCRIPTION
	"The ouput power factor of slave2." 
	::= { slave2OutputPowerfactor 25}
		
slave2OutputPowerfactorTwentysix OBJECT-TYPE
    SYNTAX      DisplayString
    MAX-ACCESS  read-only
    STATUS      current
    DESCRIPTION
	"The ouput power factor of slave2." 
	::= { slave2OutputPowerfactor 26}
		
slave2OutputPowerfactorTwentyseven OBJECT-TYPE
    SYNTAX      DisplayString
    MAX-ACCESS  read-only
    STATUS      current
    DESCRIPTION
	"The ouput power factor of slave2." 
	::= { slave2OutputPowerfactor 27}
		
slave2OutputPowerfactorTwentyeight OBJECT-TYPE
    SYNTAX      DisplayString
    MAX-ACCESS  read-only
    STATUS      current
    DESCRIPTION
	"The ouput power factor of slave2." 
	::= { slave2OutputPowerfactor 28}
		
slave2OutputPowerfactorTwentynine OBJECT-TYPE
    SYNTAX      DisplayString
    MAX-ACCESS  read-only
    STATUS      current
    DESCRIPTION
	"The ouput power factor of slave2." 
	::= { slave2OutputPowerfactor 29}
		
slave2OutputPowerfactorThirty OBJECT-TYPE
    SYNTAX      DisplayString
    MAX-ACCESS  read-only
    STATUS      current
    DESCRIPTION
	"The ouput power factor of slave2." 
	::= { slave2OutputPowerfactor 30}
		
slave2OutputPowerfactorThirtyone OBJECT-TYPE
    SYNTAX      DisplayString
    MAX-ACCESS  read-only
    STATUS      current
    DESCRIPTION
	"The ouput power factor of slave2." 
	::= { slave2OutputPowerfactor 31}
		
slave2OutputPowerfactorThirtytwo OBJECT-TYPE
    SYNTAX      DisplayString
    MAX-ACCESS  read-only
    STATUS      current
    DESCRIPTION
	"The ouput power factor of slave2." 
	::= { slave2OutputPowerfactor 32}
		
slave2OutputPowerfactorThirtythree OBJECT-TYPE
    SYNTAX      DisplayString
    MAX-ACCESS  read-only
    STATUS      current
    DESCRIPTION
	"The ouput power factor of slave2." 
	::= { slave2OutputPowerfactor 33}	
	
slave2OutputPowerfactorThirtyfour OBJECT-TYPE
    SYNTAX      DisplayString
    MAX-ACCESS  read-only
    STATUS      current
    DESCRIPTION
	"The ouput power factor of slave2." 
	::= { slave2OutputPowerfactor 34}
	
	
slave2OutputPowerfactorThirtyfive OBJECT-TYPE
    SYNTAX      DisplayString
    MAX-ACCESS  read-only
    STATUS      current
    DESCRIPTION
	"The ouput power factor of slave2." 
	::= { slave2OutputPowerfactor 35}
		
slave2OutputPowerfactorThirtysix OBJECT-TYPE
    SYNTAX      DisplayString
    MAX-ACCESS  read-only
    STATUS      current
    DESCRIPTION
	"The ouput power factor of slave2." 
	::= { slave2OutputPowerfactor 36}
		
slave2OutputPowerfactorThirtyseven OBJECT-TYPE
    SYNTAX      DisplayString
    MAX-ACCESS  read-only
    STATUS      current
    DESCRIPTION
	"The ouput power factor of slave2." 
	::= { slave2OutputPowerfactor 37}
		
slave2OutputPowerfactorThirtyeight OBJECT-TYPE
    SYNTAX      DisplayString
    MAX-ACCESS  read-only
    STATUS      current
    DESCRIPTION
	"The ouput power factor of slave2." 
	::= { slave2OutputPowerfactor 38}
		
slave2OutputPowerfactorThirtynine OBJECT-TYPE
    SYNTAX      DisplayString
    MAX-ACCESS  read-only
    STATUS      current
    DESCRIPTION
	"The ouput power factor of slave2." 
	::= { slave2OutputPowerfactor 39}
		
slave2OutputPowerfactorFourty OBJECT-TYPE
    SYNTAX      DisplayString
    MAX-ACCESS  read-only
    STATUS      current
    DESCRIPTION
	"The ouput power factor of slave2." 
	::= { slave2OutputPowerfactor 40}
		
slave2OutputPowerfactorFourtyone OBJECT-TYPE
    SYNTAX      DisplayString
    MAX-ACCESS  read-only
    STATUS      current
    DESCRIPTION
	"The ouput power factor of slave2." 
	::= { slave2OutputPowerfactor 41}
		
slave2OutputPowerfactorFourtytwo OBJECT-TYPE
    SYNTAX      DisplayString
    MAX-ACCESS  read-only
    STATUS      current
    DESCRIPTION
	"The ouput power factor of slave2." 
	::= { slave2OutputPowerfactor 42}	
	
-------------------------------slave2 output energy------------------------	
slave2OutputEnergy OBJECT IDENTIFIER ::= { slave2 10}

slave2OutputEnergyOne OBJECT-TYPE
    SYNTAX      DisplayString
    MAX-ACCESS  read-only
    STATUS      current
    DESCRIPTION
	"The ouput power of slave2." 
	::= { slave2OutputEnergy 1}

slave2OutputEnergyTwo OBJECT-TYPE
    SYNTAX      DisplayString
    MAX-ACCESS  read-only
    STATUS      current
    DESCRIPTION
	"The ouput power of slave2." 
	::= { slave2OutputEnergy 2}
	
slave2OutputEnergyThree OBJECT-TYPE
    SYNTAX      DisplayString
    MAX-ACCESS  read-only
    STATUS      current
    DESCRIPTION
	"The ouput power of slave2." 
	::= { slave2OutputEnergy 3}
	
slave2OutputEnergyFour OBJECT-TYPE
    SYNTAX      DisplayString
    MAX-ACCESS  read-only
    STATUS      current
    DESCRIPTION
	"The ouput power of slave2." 
	::= { slave2OutputEnergy 4}
		
slave2OutputEnergyFive OBJECT-TYPE
    SYNTAX      DisplayString
    MAX-ACCESS  read-only
    STATUS      current
    DESCRIPTION
	"The ouput power of slave2." 
	::= { slave2OutputEnergy 5}
	
slave2OutputEnergySix OBJECT-TYPE
    SYNTAX      DisplayString
    MAX-ACCESS  read-only
    STATUS      current
    DESCRIPTION
	"The ouput power of slave2." 
	::= { slave2OutputEnergy 6}
	
slave2OutputEnergySeven OBJECT-TYPE
    SYNTAX      DisplayString
    MAX-ACCESS  read-only
    STATUS      current
    DESCRIPTION
	"The ouput power of slave2." 
	::= { slave2OutputEnergy 7}	
	
slave2OutputEnergyEight OBJECT-TYPE
    SYNTAX      DisplayString
    MAX-ACCESS  read-only
    STATUS      current
    DESCRIPTION
	"The ouput power of slave2." 
	::= { slave2OutputEnergy 8}
	
slave2OutputEnergyNine OBJECT-TYPE
    SYNTAX      DisplayString
    MAX-ACCESS  read-only
    STATUS      current
    DESCRIPTION
	"The ouput power of slave2." 
	::= { slave2OutputEnergy 9}
		
slave2OutputEnergyTen OBJECT-TYPE
    SYNTAX      DisplayString
    MAX-ACCESS  read-only
    STATUS      current
    DESCRIPTION
	"The ouput power of slave2." 
	::= { slave2OutputEnergy 10}
		
slave2OutputEnergyEleven OBJECT-TYPE
    SYNTAX      DisplayString
    MAX-ACCESS  read-only
    STATUS      current
    DESCRIPTION
	"The ouput power of slave2." 
	::= { slave2OutputEnergy 11}
		
slave2OutputEnergyTwel OBJECT-TYPE
    SYNTAX      DisplayString
    MAX-ACCESS  read-only
    STATUS      current
    DESCRIPTION
	"The ouput power of slave2." 
	::= { slave2OutputEnergy 12}
		
slave2OutputEnergyThirteen OBJECT-TYPE
    SYNTAX      DisplayString
    MAX-ACCESS  read-only
    STATUS      current
    DESCRIPTION
	"The ouput power of slave2." 
	::= { slave2OutputEnergy 13}
		
slave2OutputEnergyFourteen OBJECT-TYPE
    SYNTAX      DisplayString
    MAX-ACCESS  read-only
    STATUS      current
    DESCRIPTION
	"The ouput power of slave2." 
	::= { slave2OutputEnergy 14}
		
slave2OutputEnergyFifteen OBJECT-TYPE
    SYNTAX      DisplayString
    MAX-ACCESS  read-only
    STATUS      current
    DESCRIPTION
	"The ouput power of slave2." 
	::= { slave2OutputEnergy 15}
		
slave2OutputEnergySixteen OBJECT-TYPE
    SYNTAX      DisplayString
    MAX-ACCESS  read-only
    STATUS      current
    DESCRIPTION
	"The ouput power of slave2." 
	::= { slave2OutputEnergy 16}
		
slave2OutputEnergySeventeen OBJECT-TYPE
    SYNTAX      DisplayString
    MAX-ACCESS  read-only
    STATUS      current
    DESCRIPTION
	"The ouput power of slave2." 
	::= { slave2OutputEnergy 17}
		
slave2OutputEnergyEighteen OBJECT-TYPE
    SYNTAX      DisplayString
    MAX-ACCESS  read-only
    STATUS      current
    DESCRIPTION
	"The ouput power of slave2." 
	::= { slave2OutputEnergy 18}
		
slave2OutputEnergyNineteen OBJECT-TYPE
    SYNTAX      DisplayString
    MAX-ACCESS  read-only
    STATUS      current
    DESCRIPTION
	"The ouput power of slave2." 
	::= { slave2OutputEnergy 19}
		
slave2OutputEnergyTwenty OBJECT-TYPE
    SYNTAX      DisplayString
    MAX-ACCESS  read-only
    STATUS      current
    DESCRIPTION
	"The ouput power of slave2." 
	::= { slave2OutputEnergy 20}
		
slave2OutputEnergyTwentyone OBJECT-TYPE
    SYNTAX      DisplayString
    MAX-ACCESS  read-only
    STATUS      current
    DESCRIPTION
	"The ouput power of slave2." 
	::= { slave2OutputEnergy 21}
		
slave2OutputEnergyTwentytwo OBJECT-TYPE
    SYNTAX      DisplayString
    MAX-ACCESS  read-only
    STATUS      current
    DESCRIPTION
	"The ouput power of slave2." 
	::= { slave2OutputEnergy 22}
		
slave2OutputEnergyTwentythree OBJECT-TYPE
    SYNTAX      DisplayString
    MAX-ACCESS  read-only
    STATUS      current
    DESCRIPTION
	"The ouput power of slave2." 
	::= { slave2OutputEnergy 23}
		
slave2OutputEnergyTwentyfour OBJECT-TYPE
    SYNTAX      DisplayString
    MAX-ACCESS  read-only
    STATUS      current
    DESCRIPTION
	"The ouput power of slave2." 
	::= { slave2OutputEnergy 24}
		
slave2OutputEnergyTwentyfive OBJECT-TYPE
    SYNTAX      DisplayString
    MAX-ACCESS  read-only
    STATUS      current
    DESCRIPTION
	"The ouput power of slave2." 
	::= { slave2OutputEnergy 25}
		
slave2OutputEnergyTwentysix OBJECT-TYPE
    SYNTAX      DisplayString
    MAX-ACCESS  read-only
    STATUS      current
    DESCRIPTION
	"The ouput power of slave2." 
	::= { slave2OutputEnergy 26}
		
slave2OutputEnergyTwentyseven OBJECT-TYPE
    SYNTAX      DisplayString
    MAX-ACCESS  read-only
    STATUS      current
    DESCRIPTION
	"The ouput power of slave2." 
	::= { slave2OutputEnergy 27}
		
slave2OutputEnergyTwentyeight OBJECT-TYPE
    SYNTAX      DisplayString
    MAX-ACCESS  read-only
    STATUS      current
    DESCRIPTION
	"The ouput power of slave2." 
	::= { slave2OutputEnergy 28}
		
slave2OutputEnergyTwentynine OBJECT-TYPE
    SYNTAX      DisplayString
    MAX-ACCESS  read-only
    STATUS      current
    DESCRIPTION
	"The ouput power of slave2." 
	::= { slave2OutputEnergy 29}
		
slave2OutputEnergyThirty OBJECT-TYPE
    SYNTAX      DisplayString
    MAX-ACCESS  read-only
    STATUS      current
    DESCRIPTION
	"The ouput power of slave2." 
	::= { slave2OutputEnergy 30}
		
slave2OutputEnergyThirtyone OBJECT-TYPE
    SYNTAX      DisplayString
    MAX-ACCESS  read-only
    STATUS      current
    DESCRIPTION
	"The ouput power of slave2." 
	::= { slave2OutputEnergy 31}
		
slave2OutputEnergyThirtytwo OBJECT-TYPE
    SYNTAX      DisplayString
    MAX-ACCESS  read-only
    STATUS      current
    DESCRIPTION
	"The ouput power of slave2." 
	::= { slave2OutputEnergy 32}
		
slave2OutputEnergyThirtythree OBJECT-TYPE
    SYNTAX      DisplayString
    MAX-ACCESS  read-only
    STATUS      current
    DESCRIPTION
	"The ouput power of slave2." 
	::= { slave2OutputEnergy 33}	
	
slave2OutputEnergyThirtyfour OBJECT-TYPE
    SYNTAX      DisplayString
    MAX-ACCESS  read-only
    STATUS      current
    DESCRIPTION
	"The ouput power of slave2." 
	::= { slave2OutputEnergy 34}
	
	
slave2OutputEnergyThirtyfive OBJECT-TYPE
    SYNTAX      DisplayString
    MAX-ACCESS  read-only
    STATUS      current
    DESCRIPTION
	"The ouput power of slave2." 
	::= { slave2OutputEnergy 35}
		
slave2OutputEnergyThirtysix OBJECT-TYPE
    SYNTAX      DisplayString
    MAX-ACCESS  read-only
    STATUS      current
    DESCRIPTION
	"The ouput power of slave2." 
	::= { slave2OutputEnergy 36}
		
slave2OutputEnergyThirtyseven OBJECT-TYPE
    SYNTAX      DisplayString
    MAX-ACCESS  read-only
    STATUS      current
    DESCRIPTION
	"The ouput power of slave2." 
	::= { slave2OutputEnergy 37}
		
slave2OutputEnergyThirtyeight OBJECT-TYPE
    SYNTAX      DisplayString
    MAX-ACCESS  read-only
    STATUS      current
    DESCRIPTION
	"The ouput power of slave2." 
	::= { slave2OutputEnergy 38}
		
slave2OutputEnergyThirtynine OBJECT-TYPE
    SYNTAX      DisplayString
    MAX-ACCESS  read-only
    STATUS      current
    DESCRIPTION
	"The ouput power of slave2." 
	::= { slave2OutputEnergy 39}
		
slave2OutputEnergyFourty OBJECT-TYPE
    SYNTAX      DisplayString
    MAX-ACCESS  read-only
    STATUS      current
    DESCRIPTION
	"The ouput power of slave2." 
	::= { slave2OutputEnergy 40}
		
slave2OutputEnergyFourtyone OBJECT-TYPE
    SYNTAX      DisplayString
    MAX-ACCESS  read-only
    STATUS      current
    DESCRIPTION
	"The ouput power of slave2." 
	::= { slave2OutputEnergy 41}
		
slave2OutputEnergyFourtytwo OBJECT-TYPE
    SYNTAX      DisplayString
    MAX-ACCESS  read-only
    STATUS      current
    DESCRIPTION
	"The ouput power of slave2." 
	::= { slave2OutputEnergy 42}	
	



-------------------------------slave3 information--------------------
slave3 OBJECT IDENTIFIER ::= { pdu 4}
slave3Information OBJECT IDENTIFIER ::= { slave3 1}
slave3Name OBJECT-TYPE
    SYNTAX      DisplayString
    MAX-ACCESS  read-write
    STATUS      current
    DESCRIPTION
	"This is the first device."
    ::= { slave3Information 1}
    
slave3Type OBJECT-TYPE
    SYNTAX      DisplayString
    MAX-ACCESS  read-only
    STATUS      current
    DESCRIPTION
	"This is device type "
    ::= { slave3Information 2}
    
slave3OutputNumber OBJECT-TYPE 
    SYNTAX      Integer32
    MAX-ACCESS  read-only
    STATUS      current
    DESCRIPTION
	"This is the number of output bits"
	::= { slave3Information 3}
	
slave3MacAdress OBJECT-TYPE
    SYNTAX      DisplayString
    MAX-ACCESS  read-only
    STATUS      current
    DESCRIPTION
	"This is device MAC adress"
    ::= { slave3Information 4}	

slave3Vison OBJECT-TYPE
    SYNTAX      DisplayString
    MAX-ACCESS  read-only
    STATUS      current
    DESCRIPTION
	"This is device vison "
    ::= { slave3Information 5}

slave3Frequency OBJECT-TYPE
    SYNTAX      Integer32
    MAX-ACCESS  read-only
    STATUS      current
    DESCRIPTION
	"This is device frequency "
    ::= { slave3Information 6}
	
slave3Emission OBJECT-TYPE
    SYNTAX      DisplayString
    MAX-ACCESS  read-only
    STATUS      current
    DESCRIPTION
	"This is device emission "
    ::= { slave3Information 7}	
	
slave3RunTime OBJECT-TYPE
    SYNTAX      DisplayString
    MAX-ACCESS  read-only
    STATUS      current
    DESCRIPTION
	"This is device running time "
    ::= { slave3Information 8}	

slave3BuzzerSwitch OBJECT-TYPE
    SYNTAX      DisplayString
    MAX-ACCESS  read-write
    STATUS      current
    DESCRIPTION
	"This is device buzzer switch."
    ::= { slave3Information 9}	

	
-------------------------------slave3 phase--------------------
slave3Phase OBJECT IDENTIFIER ::= { slave3 2}	
	
slave3PhaseOne OBJECT IDENTIFIER ::= { slave3Phase 1}	    
slave3PhaseOneCurrent OBJECT-TYPE
    SYNTAX      DisplayString
    MAX-ACCESS  read-only
    STATUS      current
    DESCRIPTION
	"The power of phase one"
    ::= { slave3PhaseOne 1}

slave3PhaseOneVoltage OBJECT-TYPE
    SYNTAX      DisplayString
    MAX-ACCESS  read-only
    STATUS      current
    DESCRIPTION
	"The power of phase one"
    ::= { slave3PhaseOne 2}

slave3PhaseOnePower OBJECT-TYPE
    SYNTAX      DisplayString
    MAX-ACCESS  read-only
    STATUS      current
    DESCRIPTION
	"The power of phase one"
    ::= { slave3PhaseOne 3}
	
slave3PhaseOnePowerfactor OBJECT-TYPE
    SYNTAX      DisplayString
    MAX-ACCESS  read-only
    STATUS      current
    DESCRIPTION
	"The power of phase one"
    ::= { slave3PhaseOne 4}	
	
slave3PhaseOneEnergy OBJECT-TYPE
    SYNTAX      DisplayString
    MAX-ACCESS  read-only
    STATUS      current
    DESCRIPTION
	"The power of phase one"
    ::= { slave3PhaseOne 5}	
		
slave3PhaseOneCurrentMin OBJECT-TYPE
    SYNTAX      DisplayString
    MAX-ACCESS  read-write
    STATUS      current
    DESCRIPTION
	"The power of phase one"
    ::= { slave3PhaseOne 6}	
	
slave3PhaseOneCurrentMinCritical OBJECT-TYPE
    SYNTAX      DisplayString
    MAX-ACCESS  read-write
    STATUS      current
    DESCRIPTION
	"The power of phase one"
    ::= { slave3PhaseOne 7}
	
slave3PhaseOneCurrentMaxCritical OBJECT-TYPE
    SYNTAX      DisplayString
    MAX-ACCESS  read-write
    STATUS      current
    DESCRIPTION
	"The power of phase one"
    ::= { slave3PhaseOne 8}
	
slave3PhaseOneCurrentMax OBJECT-TYPE
    SYNTAX      DisplayString
    MAX-ACCESS  read-write
    STATUS      current
    DESCRIPTION
	"The power of phase one"
    ::= { slave3PhaseOne 9}
	
slave3PhaseOneVoltageMin OBJECT-TYPE
    SYNTAX      DisplayString
    MAX-ACCESS  read-write
    STATUS      current
    DESCRIPTION
	"The power of phase one"
    ::= { slave3PhaseOne 10}
	
slave3PhaseOneVoltageMinCritical OBJECT-TYPE
    SYNTAX      DisplayString
    MAX-ACCESS  read-write
    STATUS      current
    DESCRIPTION
	"The power of phase one"
    ::= { slave3PhaseOne 11}

slave3PhaseOneVoltageMaxCritical OBJECT-TYPE
    SYNTAX      DisplayString
    MAX-ACCESS  read-write
    STATUS      current
    DESCRIPTION
	"The power of phase one"
    ::= { slave3PhaseOne 12}
	
slave3PhaseOneVoltageMax OBJECT-TYPE
    SYNTAX      DisplayString
    MAX-ACCESS  read-write
    STATUS      current
    DESCRIPTION
	"The power of phase one"
    ::= { slave3PhaseOne 13}


slave3PhaseTwo OBJECT IDENTIFIER ::= { slave3Phase 2}	    
slave3PhaseTwoCurrent OBJECT-TYPE
    SYNTAX      DisplayString
    MAX-ACCESS  read-only
    STATUS      current
    DESCRIPTION
	"The power of phase one"
    ::= { slave3PhaseTwo 1}

slave3PhaseTwoVoltage OBJECT-TYPE
    SYNTAX      DisplayString
    MAX-ACCESS  read-only
    STATUS      current
    DESCRIPTION
	"The power of phase one"
    ::= { slave3PhaseTwo 2}

slave3PhaseTwoPower OBJECT-TYPE
    SYNTAX      DisplayString
    MAX-ACCESS  read-only
    STATUS      current
    DESCRIPTION
	"The power of phase one"
    ::= { slave3PhaseTwo 3}
	
slave3PhaseTwoPowerfactor OBJECT-TYPE
    SYNTAX      DisplayString
    MAX-ACCESS  read-only
    STATUS      current
    DESCRIPTION
	"The power of phase one"
    ::= { slave3PhaseTwo 4}	
	
slave3PhaseTwoEnergy OBJECT-TYPE
    SYNTAX      DisplayString
    MAX-ACCESS  read-only
    STATUS      current
    DESCRIPTION
	"The power of phase one"
    ::= { slave3PhaseTwo 5}	
		
slave3PhaseTwoCurrentMin OBJECT-TYPE
    SYNTAX      DisplayString
    MAX-ACCESS  read-write
    STATUS      current
    DESCRIPTION
	"The power of phase one"
    ::= { slave3PhaseTwo 6}	
	
slave3PhaseTwoCurrentMinCritical OBJECT-TYPE
    SYNTAX      DisplayString
    MAX-ACCESS  read-write
    STATUS      current
    DESCRIPTION
	"The power of phase one"
    ::= { slave3PhaseTwo 7}
	
slave3PhaseTwoCurrentMaxCritical OBJECT-TYPE
    SYNTAX      DisplayString
    MAX-ACCESS  read-write
    STATUS      current
    DESCRIPTION
	"The power of phase one"
    ::= { slave3PhaseTwo 8}
	
slave3PhaseTwoCurrentMax OBJECT-TYPE
    SYNTAX      DisplayString
    MAX-ACCESS  read-write
    STATUS      current
    DESCRIPTION
	"The power of phase one"
    ::= { slave3PhaseTwo 9}
	
slave3PhaseTwoVoltageMin OBJECT-TYPE
    SYNTAX      DisplayString
    MAX-ACCESS  read-write
    STATUS      current
    DESCRIPTION
	"The power of phase one"
    ::= { slave3PhaseTwo 10}
	
slave3PhaseTwoVoltageMinCritical OBJECT-TYPE
    SYNTAX      DisplayString
    MAX-ACCESS  read-write
    STATUS      current
    DESCRIPTION
	"The power of phase one"
    ::= { slave3PhaseTwo 11}

slave3PhaseTwoVoltageMaxCritical OBJECT-TYPE
    SYNTAX      DisplayString
    MAX-ACCESS  read-write
    STATUS      current
    DESCRIPTION
	"The power of phase one"
    ::= { slave3PhaseTwo 12}
	
slave3PhaseTwoVoltageMax OBJECT-TYPE
    SYNTAX      DisplayString
    MAX-ACCESS  read-write
    STATUS      current
    DESCRIPTION
	"The power of phase one"
    ::= { slave3PhaseTwo 13}
	
	
slave3PhaseThree OBJECT IDENTIFIER ::= { slave3Phase 3}	    
slave3PhaseThreeCurrent OBJECT-TYPE
    SYNTAX      DisplayString
    MAX-ACCESS  read-only
    STATUS      current
    DESCRIPTION
	"The power of phase one"
    ::= { slave3PhaseThree 1}

slave3PhaseThreeVoltage OBJECT-TYPE
    SYNTAX      DisplayString
    MAX-ACCESS  read-only
    STATUS      current
    DESCRIPTION
	"The power of phase one"
    ::= { slave3PhaseThree 2}

slave3PhaseThreePower OBJECT-TYPE
    SYNTAX      DisplayString
    MAX-ACCESS  read-only
    STATUS      current
    DESCRIPTION
	"The power of phase one"
    ::= { slave3PhaseThree 3}
	
slave3PhaseThreePowerfactor OBJECT-TYPE
    SYNTAX      DisplayString
    MAX-ACCESS  read-only
    STATUS      current
    DESCRIPTION
	"The power of phase one"
    ::= { slave3PhaseThree 4}	
	
slave3PhaseThreeEnergy OBJECT-TYPE
    SYNTAX      DisplayString
    MAX-ACCESS  read-only
    STATUS      current
    DESCRIPTION
	"The power of phase one"
    ::= { slave3PhaseThree 5}	
		
slave3PhaseThreeCurrentMin OBJECT-TYPE
    SYNTAX      DisplayString
    MAX-ACCESS  read-write
    STATUS      current
    DESCRIPTION
	"The power of phase one"
    ::= { slave3PhaseThree 6}	
	
slave3PhaseThreeCurrentMinCritical OBJECT-TYPE
    SYNTAX      DisplayString
    MAX-ACCESS  read-write
    STATUS      current
    DESCRIPTION
	"The power of phase one"
    ::= { slave3PhaseThree 7}
	
slave3PhaseThreeCurrentMaxCritical OBJECT-TYPE
    SYNTAX      DisplayString
    MAX-ACCESS  read-write
    STATUS      current
    DESCRIPTION
	"The power of phase one"
    ::= { slave3PhaseThree 8}
	
slave3PhaseThreeCurrentMax OBJECT-TYPE
    SYNTAX      DisplayString
    MAX-ACCESS  read-write
    STATUS      current
    DESCRIPTION
	"The power of phase one"
    ::= { slave3PhaseThree 9}
	
slave3PhaseThreeVoltageMin OBJECT-TYPE
    SYNTAX      DisplayString
    MAX-ACCESS  read-write
    STATUS      current
    DESCRIPTION
	"The power of phase one"
    ::= { slave3PhaseThree 10}
	
slave3PhaseThreeVoltageMinCritical OBJECT-TYPE
    SYNTAX      DisplayString
    MAX-ACCESS  read-write
    STATUS      current
    DESCRIPTION
	"The power of phase one"
    ::= { slave3PhaseThree 11}

slave3PhaseThreeVoltageMaxCritical OBJECT-TYPE
    SYNTAX      DisplayString
    MAX-ACCESS  read-write
    STATUS      current
    DESCRIPTION
	"The power of phase one"
    ::= { slave3PhaseThree 12}
	
slave3PhaseThreeVoltageMax OBJECT-TYPE
    SYNTAX      DisplayString
    MAX-ACCESS  read-write
    STATUS      current
    DESCRIPTION
	"The power of phase one"
    ::= { slave3PhaseThree 13}
	
	
-------------------------------slave3 circuit--------------------	
slave3Circuit OBJECT IDENTIFIER ::= { slave3 3}	

slave3CircuitOne OBJECT IDENTIFIER ::= { slave3Circuit 1}	    
slave3CircuitOneBreaker OBJECT-TYPE
    SYNTAX      DisplayString
    MAX-ACCESS  read-only
    STATUS      current
    DESCRIPTION
	"The power of phase one"
    ::= { slave3CircuitOne 1}
	
slave3CircuitOneManagementBit OBJECT-TYPE
    SYNTAX      DisplayString
    MAX-ACCESS  read-only
    STATUS      current
    DESCRIPTION
	"The power of phase one"
    ::= { slave3CircuitOne 2}	

slave3CircuitOneCurrent OBJECT-TYPE
    SYNTAX      DisplayString
    MAX-ACCESS  read-only
    STATUS      current
    DESCRIPTION
	"The power of phase one"
    ::= { slave3CircuitOne 3}

slave3CircuitOneVoltage OBJECT-TYPE
    SYNTAX      DisplayString
    MAX-ACCESS  read-only
    STATUS      current
    DESCRIPTION
	"The power of phase one"
    ::= { slave3CircuitOne 4}

slave3CircuitOneEnergy OBJECT-TYPE
    SYNTAX      DisplayString
    MAX-ACCESS  read-only
    STATUS      current
    DESCRIPTION
	"The power of phase one"
    ::= { slave3CircuitOne 5}	
	
slave3CircuitOnePower OBJECT-TYPE
    SYNTAX      DisplayString
    MAX-ACCESS  read-only
    STATUS      current
    DESCRIPTION
	"The power of phase one"
    ::= { slave3CircuitOne 6}
	
slave3CircuitOneCurrentMin OBJECT-TYPE
    SYNTAX      DisplayString
    MAX-ACCESS  read-write
    STATUS      current
    DESCRIPTION
	"The power of phase one"
    ::= { slave3CircuitOne 7}	
	
slave3CircuitOneCurrentMinCritical OBJECT-TYPE
    SYNTAX      DisplayString
    MAX-ACCESS  read-write
    STATUS      current
    DESCRIPTION
	"The power of phase one"
    ::= { slave3CircuitOne 8}
	
slave3CircuitOneCurrentMaxCritical OBJECT-TYPE
    SYNTAX      DisplayString
    MAX-ACCESS  read-write
    STATUS      current
    DESCRIPTION
	"The power of phase one"
    ::= { slave3CircuitOne 9}
	
slave3CircuitOneCurrentMax OBJECT-TYPE
    SYNTAX      DisplayString
    MAX-ACCESS  read-write
    STATUS      current
    DESCRIPTION
	"The power of phase one"
    ::= { slave3CircuitOne 10}
	

slave3CircuitTwo OBJECT IDENTIFIER ::= { slave3Circuit 2}	    
slave3CircuitTwoBreaker OBJECT-TYPE
    SYNTAX      DisplayString
    MAX-ACCESS  read-only
    STATUS      current
    DESCRIPTION
	"The power of phase one"
    ::= { slave3CircuitTwo 1}
	
slave3CircuitTwoManagementBit OBJECT-TYPE
    SYNTAX      DisplayString
    MAX-ACCESS  read-only
    STATUS      current
    DESCRIPTION
	"The power of phase one"
    ::= { slave3CircuitTwo 2}	

slave3CircuitTwoCurrent OBJECT-TYPE
    SYNTAX      DisplayString
    MAX-ACCESS  read-only
    STATUS      current
    DESCRIPTION
	"The power of phase one"
    ::= { slave3CircuitTwo 3}

slave3CircuitTwoVoltage OBJECT-TYPE
    SYNTAX      DisplayString
    MAX-ACCESS  read-only
    STATUS      current
    DESCRIPTION
	"The power of phase one"
    ::= { slave3CircuitTwo 4}

slave3CircuitTwoEnergy OBJECT-TYPE
    SYNTAX      DisplayString
    MAX-ACCESS  read-only
    STATUS      current
    DESCRIPTION
	"The power of phase one"
    ::= { slave3CircuitTwo 5}	
	
slave3CircuitTwoPower OBJECT-TYPE
    SYNTAX      DisplayString
    MAX-ACCESS  read-only
    STATUS      current
    DESCRIPTION
	"The power of phase one"
    ::= { slave3CircuitTwo 6}
	
slave3CircuitTwoCurrentMin OBJECT-TYPE
    SYNTAX      DisplayString
    MAX-ACCESS  read-write
    STATUS      current
    DESCRIPTION
	"The power of phase one"
    ::= { slave3CircuitTwo 7}	
	
slave3CircuitTwoCurrentMinCritical OBJECT-TYPE
    SYNTAX      DisplayString
    MAX-ACCESS  read-write
    STATUS      current
    DESCRIPTION
	"The power of phase one"
    ::= { slave3CircuitTwo 8}
	
slave3CircuitTwoCurrentMaxCritical OBJECT-TYPE
    SYNTAX      DisplayString
    MAX-ACCESS  read-write
    STATUS      current
    DESCRIPTION
	"The power of phase one"
    ::= { slave3CircuitTwo 9}
	
slave3CircuitTwoCurrentMax OBJECT-TYPE
    SYNTAX      DisplayString
    MAX-ACCESS  read-write
    STATUS      current
    DESCRIPTION
	"The power of phase one"
    ::= { slave3CircuitTwo 10}
	
	
slave3CircuitThree OBJECT IDENTIFIER ::= { slave3Circuit 3}	    
slave3CircuitThreeBreaker OBJECT-TYPE
    SYNTAX      DisplayString
    MAX-ACCESS  read-only
    STATUS      current
    DESCRIPTION
	"The power of phase one"
    ::= { slave3CircuitThree 1}
	
slave3CircuitThreeManagementBit OBJECT-TYPE
    SYNTAX      DisplayString
    MAX-ACCESS  read-only
    STATUS      current
    DESCRIPTION
	"The power of phase one"
    ::= { slave3CircuitThree 2}	

slave3CircuitThreeCurrent OBJECT-TYPE
    SYNTAX      DisplayString
    MAX-ACCESS  read-only
    STATUS      current
    DESCRIPTION
	"The power of phase one"
    ::= { slave3CircuitThree 3}

slave3CircuitThreeVoltage OBJECT-TYPE
    SYNTAX      DisplayString
    MAX-ACCESS  read-only
    STATUS      current
    DESCRIPTION
	"The power of phase one"
    ::= { slave3CircuitThree 4}

slave3CircuitThreeEnergy OBJECT-TYPE
    SYNTAX      DisplayString
    MAX-ACCESS  read-only
    STATUS      current
    DESCRIPTION
	"The power of phase one"
    ::= { slave3CircuitThree 5}	
	
slave3CircuitThreePower OBJECT-TYPE
    SYNTAX      DisplayString
    MAX-ACCESS  read-only
    STATUS      current
    DESCRIPTION
	"The power of phase one"
    ::= { slave3CircuitThree 6}
	
slave3CircuitThreeCurrentMin OBJECT-TYPE
    SYNTAX      DisplayString
    MAX-ACCESS  read-write
    STATUS      current
    DESCRIPTION
	"The power of phase one"
    ::= { slave3CircuitThree 7}	
	
slave3CircuitThreeCurrentMinCritical OBJECT-TYPE
    SYNTAX      DisplayString
    MAX-ACCESS  read-write
    STATUS      current
    DESCRIPTION
	"The power of phase one"
    ::= { slave3CircuitThree 8}
	
slave3CircuitThreeCurrentMaxCritical OBJECT-TYPE
    SYNTAX      DisplayString
    MAX-ACCESS  read-write
    STATUS      current
    DESCRIPTION
	"The power of phase one"
    ::= { slave3CircuitThree 9}
	
slave3CircuitThreeCurrentMax OBJECT-TYPE
    SYNTAX      DisplayString
    MAX-ACCESS  read-write
    STATUS      current
    DESCRIPTION
	"The power of phase one"
    ::= { slave3CircuitThree 10}
	
	
slave3CircuitFour OBJECT IDENTIFIER ::= { slave3Circuit 4}	    
slave3CircuitFourBreaker OBJECT-TYPE
    SYNTAX      DisplayString
    MAX-ACCESS  read-only
    STATUS      current
    DESCRIPTION
	"The power of phase one"
    ::= { slave3CircuitFour 1}
	
slave3CircuitFourManagementBit OBJECT-TYPE
    SYNTAX      DisplayString
    MAX-ACCESS  read-only
    STATUS      current
    DESCRIPTION
	"The power of phase one"
    ::= { slave3CircuitFour 2}	

slave3CircuitFourCurrent OBJECT-TYPE
    SYNTAX      DisplayString
    MAX-ACCESS  read-only
    STATUS      current
    DESCRIPTION
	"The power of phase one"
    ::= { slave3CircuitFour 3}

slave3CircuitFourVoltage OBJECT-TYPE
    SYNTAX      DisplayString
    MAX-ACCESS  read-only
    STATUS      current
    DESCRIPTION
	"The power of phase one"
    ::= { slave3CircuitFour 4}

slave3CircuitFourEnergy OBJECT-TYPE
    SYNTAX      DisplayString
    MAX-ACCESS  read-only
    STATUS      current
    DESCRIPTION
	"The power of phase one"
    ::= { slave3CircuitFour 5}	
	
slave3CircuitFourPower OBJECT-TYPE
    SYNTAX      DisplayString
    MAX-ACCESS  read-only
    STATUS      current
    DESCRIPTION
	"The power of phase one"
    ::= { slave3CircuitFour 6}
	
slave3CircuitFourCurrentMin OBJECT-TYPE
    SYNTAX      DisplayString
    MAX-ACCESS  read-write
    STATUS      current
    DESCRIPTION
	"The power of phase one"
    ::= { slave3CircuitFour 7}	
	
slave3CircuitFourCurrentMinCritical OBJECT-TYPE
    SYNTAX      DisplayString
    MAX-ACCESS  read-write
    STATUS      current
    DESCRIPTION
	"The power of phase one"
    ::= { slave3CircuitFour 8}
	
slave3CircuitFourCurrentMaxCritical OBJECT-TYPE
    SYNTAX      DisplayString
    MAX-ACCESS  read-write
    STATUS      current
    DESCRIPTION
	"The power of phase one"
    ::= { slave3CircuitFour 9}
	
slave3CircuitFourCurrentMax OBJECT-TYPE
    SYNTAX      DisplayString
    MAX-ACCESS  read-write
    STATUS      current
    DESCRIPTION
	"The power of phase one"
    ::= { slave3CircuitFour 10}
	
	
slave3CircuitFive OBJECT IDENTIFIER ::= { slave3Circuit 5}	    
slave3CircuitFiveBreaker OBJECT-TYPE
    SYNTAX      DisplayString
    MAX-ACCESS  read-only
    STATUS      current
    DESCRIPTION
	"The power of phase one"
    ::= { slave3CircuitFive 1}
	
slave3CircuitFiveManagementBit OBJECT-TYPE
    SYNTAX      DisplayString
    MAX-ACCESS  read-only
    STATUS      current
    DESCRIPTION
	"The power of phase one"
    ::= { slave3CircuitFive 2}	

slave3CircuitFiveCurrent OBJECT-TYPE
    SYNTAX      DisplayString
    MAX-ACCESS  read-only
    STATUS      current
    DESCRIPTION
	"The power of phase one"
    ::= { slave3CircuitFive 3}

slave3CircuitFiveVoltage OBJECT-TYPE
    SYNTAX      DisplayString
    MAX-ACCESS  read-only
    STATUS      current
    DESCRIPTION
	"The power of phase one"
    ::= { slave3CircuitFive 4}

slave3CircuitFiveEnergy OBJECT-TYPE
    SYNTAX      DisplayString
    MAX-ACCESS  read-only
    STATUS      current
    DESCRIPTION
	"The power of phase one"
    ::= { slave3CircuitFive 5}	
	
slave3CircuitFivePower OBJECT-TYPE
    SYNTAX      DisplayString
    MAX-ACCESS  read-only
    STATUS      current
    DESCRIPTION
	"The power of phase one"
    ::= { slave3CircuitFive 6}
		
slave3CircuitFiveCurrentMin OBJECT-TYPE
    SYNTAX      DisplayString
    MAX-ACCESS  read-write
    STATUS      current
    DESCRIPTION
	"The power of phase one"
    ::= { slave3CircuitFive 7}	
	
slave3CircuitFiveCurrentMinCritical OBJECT-TYPE
    SYNTAX      DisplayString
    MAX-ACCESS  read-write
    STATUS      current
    DESCRIPTION
	"The power of phase one"
    ::= { slave3CircuitFive 8}
	
slave3CircuitFiveCurrentMaxCritical OBJECT-TYPE
    SYNTAX      DisplayString
    MAX-ACCESS  read-write
    STATUS      current
    DESCRIPTION
	"The power of phase one"
    ::= { slave3CircuitFive 9}
	
slave3CircuitFiveCurrentMax OBJECT-TYPE
    SYNTAX      DisplayString
    MAX-ACCESS  read-write
    STATUS      current
    DESCRIPTION
	"The power of phase one"
    ::= { slave3CircuitFive 10}

	
slave3CircuitSix OBJECT IDENTIFIER ::= { slave3Circuit 6}	    
slave3CircuitSixBreaker OBJECT-TYPE
    SYNTAX      DisplayString
    MAX-ACCESS  read-only
    STATUS      current
    DESCRIPTION
	"The power of phase one"
    ::= { slave3CircuitSix 1}
	
slave3CircuitSixManagementBit OBJECT-TYPE
    SYNTAX      DisplayString
    MAX-ACCESS  read-only
    STATUS      current
    DESCRIPTION
	"The power of phase one"
    ::= { slave3CircuitSix 2}	

slave3CircuitSixCurrent OBJECT-TYPE
    SYNTAX      DisplayString
    MAX-ACCESS  read-only
    STATUS      current
    DESCRIPTION
	"The power of phase one"
    ::= { slave3CircuitSix 3}

slave3CircuitSixVoltage OBJECT-TYPE
    SYNTAX      DisplayString
    MAX-ACCESS  read-only
    STATUS      current
    DESCRIPTION
	"The power of phase one"
    ::= { slave3CircuitSix 4}

slave3CircuitSixEnergy OBJECT-TYPE
    SYNTAX      DisplayString
    MAX-ACCESS  read-only
    STATUS      current
    DESCRIPTION
	"The power of phase one"
    ::= { slave3CircuitSix 5}	
	
slave3CircuitSixPower OBJECT-TYPE
    SYNTAX      DisplayString
    MAX-ACCESS  read-only
    STATUS      current
    DESCRIPTION
	"The power of phase one"
    ::= { slave3CircuitSix 6}
	
slave3CircuitSixCurrentMin OBJECT-TYPE
    SYNTAX      DisplayString
    MAX-ACCESS  read-write
    STATUS      current
    DESCRIPTION
	"The power of phase one"
    ::= { slave3CircuitSix 7}	
	
slave3CircuitSixCurrentMinCritical OBJECT-TYPE
    SYNTAX      DisplayString
    MAX-ACCESS  read-write
    STATUS      current
    DESCRIPTION
	"The power of phase one"
    ::= { slave3CircuitSix 8}
	
slave3CircuitSixCurrentMaxCritical OBJECT-TYPE
    SYNTAX      DisplayString
    MAX-ACCESS  read-write
    STATUS      current
    DESCRIPTION
	"The power of phase one"
    ::= { slave3CircuitSix 9}
	
slave3CircuitSixCurrentMax OBJECT-TYPE
    SYNTAX      DisplayString
    MAX-ACCESS  read-write
    STATUS      current
    DESCRIPTION
	"The power of phase one"
    ::= { slave3CircuitSix 10}

	
-------------------------------slave3 sensor------------------------	
slave3Sensor OBJECT IDENTIFIER ::= { slave3 4}
slave3SensorTemperatureOne OBJECT-TYPE
    SYNTAX      DisplayString
    MAX-ACCESS  read-only
    STATUS      current
    DESCRIPTION
	"This is the first device."
    ::= { slave3Sensor 1}
	
slave3SensorTemperatureTwo OBJECT-TYPE
    SYNTAX      DisplayString
    MAX-ACCESS  read-only
    STATUS      current
    DESCRIPTION
	"This is the first device."
    ::= { slave3Sensor 2}

slave3SensorHumidityOne OBJECT-TYPE
    SYNTAX      DisplayString
    MAX-ACCESS  read-only
    STATUS      current
    DESCRIPTION
	"This is the first device."
    ::= { slave3Sensor 3}

slave3SensorHumidityTwo OBJECT-TYPE
    SYNTAX      DisplayString
    MAX-ACCESS  read-only
    STATUS      current
    DESCRIPTION
	"This is the first device."
    ::= { slave3Sensor 4}	

slave3SensorDoorOne OBJECT-TYPE
    SYNTAX      DisplayString
    MAX-ACCESS  read-only
    STATUS      current
    DESCRIPTION
	"This is the first device."
    ::= { slave3Sensor 5}

slave3SensorDoorTwo OBJECT-TYPE
    SYNTAX      DisplayString
    MAX-ACCESS  read-only
    STATUS      current
    DESCRIPTION
	"This is the first device."
    ::= { slave3Sensor 6}	
	
slave3SensorSmoke OBJECT-TYPE
    SYNTAX      DisplayString
    MAX-ACCESS  read-only
    STATUS      current
    DESCRIPTION
	"This is the first device."
    ::= { slave3Sensor 7}
	
slave3SensorWater OBJECT-TYPE
    SYNTAX      DisplayString
    MAX-ACCESS  read-only
    STATUS      current
    DESCRIPTION
	"This is the first device."
    ::= { slave3Sensor 8}
	
slave3SensorTemperatureOneMin OBJECT-TYPE
    SYNTAX      DisplayString
    MAX-ACCESS  read-write
    STATUS      current
    DESCRIPTION
	"This is the first device."
    ::= { slave3Sensor 9}
	
slave3SensorTemperatureOneMinCritical OBJECT-TYPE
    SYNTAX      DisplayString
    MAX-ACCESS  read-write
    STATUS      current
    DESCRIPTION
	"This is the first device."
    ::= { slave3Sensor 10}	
	
slave3SensorTemperatureOneMaxCritical OBJECT-TYPE
    SYNTAX      DisplayString
    MAX-ACCESS  read-write
    STATUS      current
    DESCRIPTION
	"This is the first device."
    ::= { slave3Sensor 11}
	
slave3SensorTemperatureOneMax OBJECT-TYPE
    SYNTAX      DisplayString
    MAX-ACCESS  read-write
    STATUS      current
    DESCRIPTION
	"This is the first device."
    ::= { slave3Sensor 12}

slave3SensorTemperatureTwoMin OBJECT-TYPE
    SYNTAX      DisplayString
    MAX-ACCESS  read-write
    STATUS      current
    DESCRIPTION
	"This is the first device."
    ::= { slave3Sensor 13}
	
slave3SensorTemperatureTwoMinCritical OBJECT-TYPE
    SYNTAX      DisplayString
    MAX-ACCESS  read-write
    STATUS      current
    DESCRIPTION
	"This is the first device."
    ::= { slave3Sensor 14}	
	
slave3SensorTemperatureTwoMaxCritical OBJECT-TYPE
    SYNTAX      DisplayString
    MAX-ACCESS  read-write
    STATUS      current
    DESCRIPTION
	"This is the first device."
    ::= { slave3Sensor 15}
	
slave3SensorTemperatureTwoMax OBJECT-TYPE
    SYNTAX      DisplayString
    MAX-ACCESS  read-write
    STATUS      current
    DESCRIPTION
	"This is the first device."
    ::= { slave3Sensor 16}
	
slave3SensorHumidityOneMin OBJECT-TYPE
    SYNTAX      DisplayString
    MAX-ACCESS  read-write
    STATUS      current
    DESCRIPTION
	"This is the first device."
    ::= { slave3Sensor 17}
	
slave3SensorHumidityOneMinCritical OBJECT-TYPE
    SYNTAX      DisplayString
    MAX-ACCESS  read-write
    STATUS      current
    DESCRIPTION
	"This is the first device."
    ::= { slave3Sensor 18}	
	
slave3SensorHumidityOneMaxCritical OBJECT-TYPE
    SYNTAX      DisplayString
    MAX-ACCESS  read-write
    STATUS      current
    DESCRIPTION
	"This is the first device."
    ::= { slave3Sensor 19}
	
slave3SensorHumidityOneMax OBJECT-TYPE
    SYNTAX      DisplayString
    MAX-ACCESS  read-write
    STATUS      current
    DESCRIPTION
	"This is the first device."
    ::= { slave3Sensor 20}

slave3SensorHumidityTwoMin OBJECT-TYPE
    SYNTAX      DisplayString
    MAX-ACCESS  read-write
    STATUS      current
    DESCRIPTION
	"This is the first device."
    ::= { slave3Sensor 21}
	
slave3SensorHumidityTwoMinCritical OBJECT-TYPE
    SYNTAX      DisplayString
    MAX-ACCESS  read-write
    STATUS      current
    DESCRIPTION
	"This is the first device."
    ::= { slave3Sensor 22}	
	
slave3SensorHumidityTwoMaxCritical OBJECT-TYPE
    SYNTAX      DisplayString
    MAX-ACCESS  read-write
    STATUS      current
    DESCRIPTION
	"This is the first device."
    ::= { slave3Sensor 23}
	
slave3SensorHumidityTwoMax OBJECT-TYPE
    SYNTAX      DisplayString
    MAX-ACCESS  read-write
    STATUS      current
    DESCRIPTION
	"This is the first device."
    ::= { slave3Sensor 24}
	
-------------------------------slave3 output name------------------------	
slave3OutputName OBJECT IDENTIFIER ::= { slave3 5}
slave3OutputNameOne OBJECT-TYPE
    SYNTAX      DisplayString
    MAX-ACCESS  read-write
    STATUS      current
    DESCRIPTION
	"The first output name of slave3"
    ::= { slave3OutputName 1}

slave3OutputNameTwo OBJECT-TYPE
    SYNTAX      DisplayString
    MAX-ACCESS  read-write
    STATUS      current
    DESCRIPTION
	"The second output name of slave3"
    ::= { slave3OutputName 2}

slave3OutputNameThree OBJECT-TYPE
    SYNTAX      DisplayString
    MAX-ACCESS  read-write
    STATUS      current
    DESCRIPTION
	"The second output name of slave3"
    ::= { slave3OutputName 3}

slave3OutputNameFour OBJECT-TYPE
    SYNTAX      DisplayString
    MAX-ACCESS  read-write
    STATUS      current
    DESCRIPTION
	"The second output name of slave3"
    ::= { slave3OutputName 4}

slave3OutputNameFive OBJECT-TYPE
    SYNTAX      DisplayString
    MAX-ACCESS  read-write
    STATUS      current
    DESCRIPTION
	"The second output name of slave3"
    ::= { slave3OutputName 5}

slave3OutputNameSix OBJECT-TYPE
    SYNTAX      DisplayString
    MAX-ACCESS  read-write
    STATUS      current
    DESCRIPTION
	"The second output name of slave3"
    ::= { slave3OutputName 6}

slave3OutputNameSeven OBJECT-TYPE
    SYNTAX      DisplayString
    MAX-ACCESS  read-write
    STATUS      current
    DESCRIPTION
	"The second output name of slave3"
    ::= { slave3OutputName 7}

slave3OutputNameEight OBJECT-TYPE
    SYNTAX      DisplayString
    MAX-ACCESS  read-write
    STATUS      current
    DESCRIPTION
	"The second output name of slave3"
    ::= { slave3OutputName 8}

slave3OutputNameNine OBJECT-TYPE
    SYNTAX      DisplayString
    MAX-ACCESS  read-write
    STATUS      current
    DESCRIPTION
	"The second output name of slave3"
    ::= { slave3OutputName 9}

slave3OutputNameTen OBJECT-TYPE
    SYNTAX      DisplayString
    MAX-ACCESS  read-write
    STATUS      current
    DESCRIPTION
	"The second output name of slave3"
    ::= { slave3OutputName 10}

slave3OutputNameEleven OBJECT-TYPE
    SYNTAX      DisplayString
    MAX-ACCESS  read-write
    STATUS      current
    DESCRIPTION
	"The second output name of slave3"
    ::= { slave3OutputName 11}

slave3OutputNameTwel OBJECT-TYPE
    SYNTAX      DisplayString
    MAX-ACCESS  read-write
    STATUS      current
    DESCRIPTION
	"The second output name of slave3"
    ::= { slave3OutputName 12}

slave3OutputNameThirteen OBJECT-TYPE
    SYNTAX      DisplayString
    MAX-ACCESS  read-write
    STATUS      current
    DESCRIPTION
	"The second output name of slave3"
    ::= { slave3OutputName 13}

slave3OutputNameFourteen OBJECT-TYPE
    SYNTAX      DisplayString
    MAX-ACCESS  read-write
    STATUS      current
    DESCRIPTION
	"The second output name of slave3"
    ::= { slave3OutputName 14}

slave3OutputNameFifteen OBJECT-TYPE
    SYNTAX      DisplayString
    MAX-ACCESS  read-write
    STATUS      current
    DESCRIPTION
	"The second output name of slave3"
    ::= { slave3OutputName 15}

slave3OutputNameSixteen OBJECT-TYPE
    SYNTAX      DisplayString
    MAX-ACCESS  read-write
    STATUS      current
    DESCRIPTION
	"The second output name of slave3"
    ::= { slave3OutputName 16}

slave3OutputNameSeventeen OBJECT-TYPE
    SYNTAX      DisplayString
    MAX-ACCESS  read-write
    STATUS      current
    DESCRIPTION
	"The second output name of slave3"
    ::= { slave3OutputName 17}

slave3OutputNameEighteen OBJECT-TYPE
    SYNTAX      DisplayString
    MAX-ACCESS  read-write
    STATUS      current
    DESCRIPTION
	"The second output name of slave3"
    ::= { slave3OutputName 18}
	
slave3OutputNameNineteen OBJECT-TYPE
    SYNTAX      DisplayString
    MAX-ACCESS  read-write
    STATUS      current
    DESCRIPTION
	"The second output name of slave3"
    ::= { slave3OutputName 19}
	
slave3OutputNametwenty OBJECT-TYPE
    SYNTAX      DisplayString
    MAX-ACCESS  read-write
    STATUS      current
    DESCRIPTION
	"The second output name of slave3"
    ::= { slave3OutputName 20}
	
slave3OutputNameTwentyone OBJECT-TYPE
    SYNTAX      DisplayString
    MAX-ACCESS  read-write
    STATUS      current
    DESCRIPTION
	"The second output name of slave3"
    ::= { slave3OutputName 21}
	
slave3OutputNameTwentyonetwo OBJECT-TYPE
    SYNTAX      DisplayString
    MAX-ACCESS  read-write
    STATUS      current
    DESCRIPTION
	"The second output name of slave3"
    ::= { slave3OutputName 22}
	
slave3OutputNameTwentythree OBJECT-TYPE
    SYNTAX      DisplayString
    MAX-ACCESS  read-write
    STATUS      current
    DESCRIPTION
	"The second output name of slave3"
    ::= { slave3OutputName 23}
	
slave3OutputNameTwentyfour OBJECT-TYPE
    SYNTAX      DisplayString
    MAX-ACCESS  read-write
    STATUS      current
    DESCRIPTION
	"The second output name of slave3"
    ::= { slave3OutputName 24}
	
slave3OutputNameTwentyfive OBJECT-TYPE
    SYNTAX      DisplayString
    MAX-ACCESS  read-write
    STATUS      current
    DESCRIPTION
	"The second output name of slave3"
    ::= { slave3OutputName 25}
	
slave3OutputNameTwentysix OBJECT-TYPE
    SYNTAX      DisplayString
    MAX-ACCESS  read-write
    STATUS      current
    DESCRIPTION
	"The second output name of slave3"
    ::= { slave3OutputName 26}
	
slave3OutputNameTwentyseven OBJECT-TYPE
    SYNTAX      DisplayString
    MAX-ACCESS  read-write
    STATUS      current
    DESCRIPTION
	"The second output name of slave3"
    ::= { slave3OutputName 27}
	
slave3OutputNameTwentyeight OBJECT-TYPE
    SYNTAX      DisplayString
    MAX-ACCESS  read-write
    STATUS      current
    DESCRIPTION
	"The second output name of slave3"
    ::= { slave3OutputName 28}	
slave3OutputNameTwentynine OBJECT-TYPE
    SYNTAX      DisplayString
    MAX-ACCESS  read-write
    STATUS      current
    DESCRIPTION
	"The second output name of slave3"
    ::= { slave3OutputName 29}
	
slave3OutputNameThirty OBJECT-TYPE
    SYNTAX      DisplayString
    MAX-ACCESS  read-write
    STATUS      current
    DESCRIPTION
	"The second output name of slave3"
    ::= { slave3OutputName 30}
	
slave3OutputNameThirtyone OBJECT-TYPE
    SYNTAX      DisplayString
    MAX-ACCESS  read-write
    STATUS      current
    DESCRIPTION
	"The second output name of slave3"
    ::= { slave3OutputName 31}
	
slave3OutputNameThirtytwo OBJECT-TYPE
    SYNTAX      DisplayString
    MAX-ACCESS  read-write
    STATUS      current
    DESCRIPTION
	"The second output name of slave3"
    ::= { slave3OutputName 32}
	
slave3OutputNameThirtythree OBJECT-TYPE
    SYNTAX      DisplayString
    MAX-ACCESS  read-write
    STATUS      current
    DESCRIPTION
	"The second output name of slave3"
    ::= { slave3OutputName 33}
	
slave3OutputNameThirtyfour OBJECT-TYPE
    SYNTAX      DisplayString
    MAX-ACCESS  read-write
    STATUS      current
    DESCRIPTION
	"The second output name of slave3"
    ::= { slave3OutputName 34}
	
slave3OutputNameThirtyfive OBJECT-TYPE
    SYNTAX      DisplayString
    MAX-ACCESS  read-write
    STATUS      current
    DESCRIPTION
	"The second output name of slave3"
    ::= { slave3OutputName 35}
	
slave3OutputNameThirtysix OBJECT-TYPE
    SYNTAX      DisplayString
    MAX-ACCESS  read-write
    STATUS      current
    DESCRIPTION
	"The second output name of slave3"
    ::= { slave3OutputName 36}
	
slave3OutputNameThirtyseven OBJECT-TYPE
    SYNTAX      DisplayString
    MAX-ACCESS  read-write
    STATUS      current
    DESCRIPTION
	"The second output name of slave3"
    ::= { slave3OutputName 37}
	
slave3OutputNameThirtyeight OBJECT-TYPE
    SYNTAX      DisplayString
    MAX-ACCESS  read-write
    STATUS      current
    DESCRIPTION
	"The second output name of slave3"
    ::= { slave3OutputName 38}
	
slave3OutputNameThirtynine OBJECT-TYPE
    SYNTAX      DisplayString
    MAX-ACCESS  read-write
    STATUS      current
    DESCRIPTION
	"The second output name of slave3"
    ::= { slave3OutputName 39}
	
slave3OutputNameFourty OBJECT-TYPE
    SYNTAX      DisplayString
    MAX-ACCESS  read-write
    STATUS      current
    DESCRIPTION
	"The second output name of slave3"
    ::= { slave3OutputName 40}
	
slave3OutputNameFourtyone OBJECT-TYPE
    SYNTAX      DisplayString
    MAX-ACCESS  read-write
    STATUS      current
    DESCRIPTION
	"The second output name of slave3"
    ::= { slave3OutputName 41}
	
slave3OutputNameFourtytwo OBJECT-TYPE
    SYNTAX      DisplayString
    MAX-ACCESS  read-write
    STATUS      current
    DESCRIPTION
	"The second output name of slave3"
    ::= { slave3OutputName 42}	

	
-------------------------------slave3 output delay------------------------	
slave3OutputDelay OBJECT IDENTIFIER ::= { slave3 6}	
slave3OutputDelayOne OBJECT-TYPE
    SYNTAX      DisplayString
    MAX-ACCESS  read-write
    STATUS      current
    DESCRIPTION
	"The first output name of slave3"
    ::= { slave3OutputDelay 1}

slave3OutputDelayTwo OBJECT-TYPE
    SYNTAX      DisplayString
    MAX-ACCESS  read-write
    STATUS      current
    DESCRIPTION
	"The second output name of slave3"
    ::= { slave3OutputDelay 2}

slave3OutputDelayThree OBJECT-TYPE
    SYNTAX      DisplayString
    MAX-ACCESS  read-write
    STATUS      current
    DESCRIPTION
	"The second output name of slave3"
    ::= { slave3OutputDelay 3}

slave3OutputDelayFour OBJECT-TYPE
    SYNTAX      DisplayString
    MAX-ACCESS  read-write
    STATUS      current
    DESCRIPTION
	"The second output name of slave3"
    ::= { slave3OutputDelay 4}

slave3OutputDelayFive OBJECT-TYPE
    SYNTAX      DisplayString
    MAX-ACCESS  read-write
    STATUS      current
    DESCRIPTION
	"The second output name of slave3"
    ::= { slave3OutputDelay 5}

slave3OutputDelaySix OBJECT-TYPE
    SYNTAX      DisplayString
    MAX-ACCESS  read-write
    STATUS      current
    DESCRIPTION
	"The second output name of slave3"
    ::= { slave3OutputDelay 6}

slave3OutputDelaySeven OBJECT-TYPE
    SYNTAX      DisplayString
    MAX-ACCESS  read-write
    STATUS      current
    DESCRIPTION
	"The second output name of slave3"
    ::= { slave3OutputDelay 7}

slave3OutputDelayEight OBJECT-TYPE
    SYNTAX      DisplayString
    MAX-ACCESS  read-write
    STATUS      current
    DESCRIPTION
	"The second output name of slave3"
    ::= { slave3OutputDelay 8}

slave3OutputDelayNine OBJECT-TYPE
    SYNTAX      DisplayString
    MAX-ACCESS  read-write
    STATUS      current
    DESCRIPTION
	"The second output name of slave3"
    ::= { slave3OutputDelay 9}

slave3OutputDelayTen OBJECT-TYPE
    SYNTAX      DisplayString
    MAX-ACCESS  read-write
    STATUS      current
    DESCRIPTION
	"The second output name of slave3"
    ::= { slave3OutputDelay 10}

slave3OutputDelayEleven OBJECT-TYPE
    SYNTAX      DisplayString
    MAX-ACCESS  read-write
    STATUS      current
    DESCRIPTION
	"The second output name of slave3"
    ::= { slave3OutputDelay 11}

slave3OutputDelayTwel OBJECT-TYPE
    SYNTAX      DisplayString
    MAX-ACCESS  read-write
    STATUS      current
    DESCRIPTION
	"The second output name of slave3"
    ::= { slave3OutputDelay 12}

slave3OutputDelayThirteen OBJECT-TYPE
    SYNTAX      DisplayString
    MAX-ACCESS  read-write
    STATUS      current
    DESCRIPTION
	"The second output name of slave3"
    ::= { slave3OutputDelay 13}

slave3OutputDelayFourteen OBJECT-TYPE
    SYNTAX      DisplayString
    MAX-ACCESS  read-write
    STATUS      current
    DESCRIPTION
	"The second output name of slave3"
    ::= { slave3OutputDelay 14}

slave3OutputDelayFifteen OBJECT-TYPE
    SYNTAX      DisplayString
    MAX-ACCESS  read-write
    STATUS      current
    DESCRIPTION
	"The second output name of slave3"
    ::= { slave3OutputDelay 15}

slave3OutputDelaySixteen OBJECT-TYPE
    SYNTAX      DisplayString
    MAX-ACCESS  read-write
    STATUS      current
    DESCRIPTION
	"The second output name of slave3"
    ::= { slave3OutputDelay 16}

slave3OutputDelaySeventeen OBJECT-TYPE
    SYNTAX      DisplayString
    MAX-ACCESS  read-write
    STATUS      current
    DESCRIPTION
	"The second output name of slave3"
    ::= { slave3OutputDelay 17}

slave3OutputDelayEighteen OBJECT-TYPE
    SYNTAX      DisplayString
    MAX-ACCESS  read-write
    STATUS      current
    DESCRIPTION
	"The second output name of slave3"
    ::= { slave3OutputDelay 18}
	
slave3OutputDelayNineteen OBJECT-TYPE
    SYNTAX      DisplayString
    MAX-ACCESS  read-write
    STATUS      current
    DESCRIPTION
	"The second output name of slave3"
    ::= { slave3OutputDelay 19}
	
slave3OutputDelaytwenty OBJECT-TYPE
    SYNTAX      DisplayString
    MAX-ACCESS  read-write
    STATUS      current
    DESCRIPTION
	"The second output name of slave3"
    ::= { slave3OutputDelay 20}
	
slave3OutputDelayTwentyone OBJECT-TYPE
    SYNTAX      DisplayString
    MAX-ACCESS  read-write
    STATUS      current
    DESCRIPTION
	"The second output name of slave3"
    ::= { slave3OutputDelay 21}
	
slave3OutputDelayTwentyonetwo OBJECT-TYPE
    SYNTAX      DisplayString
    MAX-ACCESS  read-write
    STATUS      current
    DESCRIPTION
	"The second output name of slave3"
    ::= { slave3OutputDelay 22}
	
slave3OutputDelayTwentythree OBJECT-TYPE
    SYNTAX      DisplayString
    MAX-ACCESS  read-write
    STATUS      current
    DESCRIPTION
	"The second output name of slave3"
    ::= { slave3OutputDelay 23}
	
slave3OutputDelayTwentyfour OBJECT-TYPE
    SYNTAX      DisplayString
    MAX-ACCESS  read-write
    STATUS      current
    DESCRIPTION
	"The second output name of slave3"
    ::= { slave3OutputDelay 24}
	
slave3OutputDelayTwentyfive OBJECT-TYPE
    SYNTAX      DisplayString
    MAX-ACCESS  read-write
    STATUS      current
    DESCRIPTION
	"The second output name of slave3"
    ::= { slave3OutputDelay 25}
	
slave3OutputDelayTwentysix OBJECT-TYPE
    SYNTAX      DisplayString
    MAX-ACCESS  read-write
    STATUS      current
    DESCRIPTION
	"The second output name of slave3"
    ::= { slave3OutputDelay 26}
	
slave3OutputDelayTwentyseven OBJECT-TYPE
    SYNTAX      DisplayString
    MAX-ACCESS  read-write
    STATUS      current
    DESCRIPTION
	"The second output name of slave3"
    ::= { slave3OutputDelay 27}
	
slave3OutputDelayTwentyeight OBJECT-TYPE
    SYNTAX      DisplayString
    MAX-ACCESS  read-write
    STATUS      current
    DESCRIPTION
	"The second output name of slave3"
    ::= { slave3OutputDelay 28}	
slave3OutputDelayTwentynine OBJECT-TYPE
    SYNTAX      DisplayString
    MAX-ACCESS  read-write
    STATUS      current
    DESCRIPTION
	"The second output name of slave3"
    ::= { slave3OutputDelay 29}
	
slave3OutputDelayThirty OBJECT-TYPE
    SYNTAX      DisplayString
    MAX-ACCESS  read-write
    STATUS      current
    DESCRIPTION
	"The second output name of slave3"
    ::= { slave3OutputDelay 30}
	
slave3OutputDelayThirtyone OBJECT-TYPE
    SYNTAX      DisplayString
    MAX-ACCESS  read-write
    STATUS      current
    DESCRIPTION
	"The second output name of slave3"
    ::= { slave3OutputDelay 31}
	
slave3OutputDelayThirtytwo OBJECT-TYPE
    SYNTAX      DisplayString
    MAX-ACCESS  read-write
    STATUS      current
    DESCRIPTION
	"The second output name of slave3"
    ::= { slave3OutputDelay 32}
	
slave3OutputDelayThirtythree OBJECT-TYPE
    SYNTAX      DisplayString
    MAX-ACCESS  read-write
    STATUS      current
    DESCRIPTION
	"The second output name of slave3"
    ::= { slave3OutputDelay 33}
	
slave3OutputDelayThirtyfour OBJECT-TYPE
    SYNTAX      DisplayString
    MAX-ACCESS  read-write
    STATUS      current
    DESCRIPTION
	"The second output name of slave3"
    ::= { slave3OutputDelay 34}
	
slave3OutputDelayThirtyfive OBJECT-TYPE
    SYNTAX      DisplayString
    MAX-ACCESS  read-write
    STATUS      current
    DESCRIPTION
	"The second output name of slave3"
    ::= { slave3OutputDelay 35}
	
slave3OutputDelayThirtysix OBJECT-TYPE
    SYNTAX      DisplayString
    MAX-ACCESS  read-write
    STATUS      current
    DESCRIPTION
	"The second output name of slave3"
    ::= { slave3OutputDelay 36}
	
slave3OutputDelayThirtyseven OBJECT-TYPE
    SYNTAX      DisplayString
    MAX-ACCESS  read-write
    STATUS      current
    DESCRIPTION
	"The second output name of slave3"
    ::= { slave3OutputDelay 37}
	
slave3OutputDelayThirtyeight OBJECT-TYPE
    SYNTAX      DisplayString
    MAX-ACCESS  read-write
    STATUS      current
    DESCRIPTION
	"The second output name of slave3"
    ::= { slave3OutputDelay 38}
	
slave3OutputDelayThirtynine OBJECT-TYPE
    SYNTAX      DisplayString
    MAX-ACCESS  read-write
    STATUS      current
    DESCRIPTION
	"The second output name of slave3"
    ::= { slave3OutputDelay 39}
	
slave3OutputDelayFourty OBJECT-TYPE
    SYNTAX      DisplayString
    MAX-ACCESS  read-write
    STATUS      current
    DESCRIPTION
	"The second output name of slave3"
    ::= { slave3OutputDelay 40}
	
slave3OutputDelayFourtyone OBJECT-TYPE
    SYNTAX      DisplayString
    MAX-ACCESS  read-write
    STATUS      current
    DESCRIPTION
	"The second output name of slave3"
    ::= { slave3OutputDelay 41}
	
slave3OutputDelayFourtytwo OBJECT-TYPE
    SYNTAX      DisplayString
    MAX-ACCESS  read-write
    STATUS      current
    DESCRIPTION
	"The second output name of slave3"
    ::= { slave3OutputDelay 42}

	
-------------------------------slave3 output switch------------------------	
slave3OutputSwitch OBJECT IDENTIFIER ::= { slave3 7}		
slave3OutputSwitchOne OBJECT-TYPE
    SYNTAX      DisplayString
    MAX-ACCESS  read-write
    STATUS      current
    DESCRIPTION
	"The first output name of slave3"
    ::= { slave3OutputSwitch 1}

slave3OutputSwitchTwo OBJECT-TYPE
    SYNTAX      DisplayString
    MAX-ACCESS  read-write
    STATUS      current
    DESCRIPTION
	"The second output name of slave3"
    ::= { slave3OutputSwitch 2}

slave3OutputSwitchThree OBJECT-TYPE
    SYNTAX      DisplayString
    MAX-ACCESS  read-write
    STATUS      current
    DESCRIPTION
	"The second output name of slave3"
    ::= { slave3OutputSwitch 3}

slave3OutputSwitchFour OBJECT-TYPE
    SYNTAX      DisplayString
    MAX-ACCESS  read-write
    STATUS      current
    DESCRIPTION
	"The second output name of slave3"
    ::= { slave3OutputSwitch 4}

slave3OutputSwitchFive OBJECT-TYPE
    SYNTAX      DisplayString
    MAX-ACCESS  read-write
    STATUS      current
    DESCRIPTION
	"The second output name of slave3"
    ::= { slave3OutputSwitch 5}

slave3OutputSwitchSix OBJECT-TYPE
    SYNTAX      DisplayString
    MAX-ACCESS  read-write
    STATUS      current
    DESCRIPTION
	"The second output name of slave3"
    ::= { slave3OutputSwitch 6}

slave3OutputSwitchSeven OBJECT-TYPE
    SYNTAX      DisplayString
    MAX-ACCESS  read-write
    STATUS      current
    DESCRIPTION
	"The second output name of slave3"
    ::= { slave3OutputSwitch 7}

slave3OutputSwitchEight OBJECT-TYPE
    SYNTAX      DisplayString
    MAX-ACCESS  read-write
    STATUS      current
    DESCRIPTION
	"The second output name of slave3"
    ::= { slave3OutputSwitch 8}

slave3OutputSwitchNine OBJECT-TYPE
    SYNTAX      DisplayString
    MAX-ACCESS  read-write
    STATUS      current
    DESCRIPTION
	"The second output name of slave3"
    ::= { slave3OutputSwitch 9}

slave3OutputSwitchTen OBJECT-TYPE
    SYNTAX      DisplayString
    MAX-ACCESS  read-write
    STATUS      current
    DESCRIPTION
	"The second output name of slave3"
    ::= { slave3OutputSwitch 10}

slave3OutputSwitchEleven OBJECT-TYPE
    SYNTAX      DisplayString
    MAX-ACCESS  read-write
    STATUS      current
    DESCRIPTION
	"The second output name of slave3"
    ::= { slave3OutputSwitch 11}

slave3OutputSwitchTwel OBJECT-TYPE
    SYNTAX      DisplayString
    MAX-ACCESS  read-write
    STATUS      current
    DESCRIPTION
	"The second output name of slave3"
    ::= { slave3OutputSwitch 12}

slave3OutputSwitchThirteen OBJECT-TYPE
    SYNTAX      DisplayString
    MAX-ACCESS  read-write
    STATUS      current
    DESCRIPTION
	"The second output name of slave3"
    ::= { slave3OutputSwitch 13}

slave3OutputSwitchFourteen OBJECT-TYPE
    SYNTAX      DisplayString
    MAX-ACCESS  read-write
    STATUS      current
    DESCRIPTION
	"The second output name of slave3"
    ::= { slave3OutputSwitch 14}

slave3OutputSwitchFifteen OBJECT-TYPE
    SYNTAX      DisplayString
    MAX-ACCESS  read-write
    STATUS      current
    DESCRIPTION
	"The second output name of slave3"
    ::= { slave3OutputSwitch 15}

slave3OutputSwitchSixteen OBJECT-TYPE
    SYNTAX      DisplayString
    MAX-ACCESS  read-write
    STATUS      current
    DESCRIPTION
	"The second output name of slave3"
    ::= { slave3OutputSwitch 16}

slave3OutputSwitchSeventeen OBJECT-TYPE
    SYNTAX      DisplayString
    MAX-ACCESS  read-write
    STATUS      current
    DESCRIPTION
	"The second output name of slave3"
    ::= { slave3OutputSwitch 17}

slave3OutputSwitchEighteen OBJECT-TYPE
    SYNTAX      DisplayString
    MAX-ACCESS  read-write
    STATUS      current
    DESCRIPTION
	"The second output name of slave3"
    ::= { slave3OutputSwitch 18}
	
slave3OutputSwitchNineteen OBJECT-TYPE
    SYNTAX      DisplayString
    MAX-ACCESS  read-write
    STATUS      current
    DESCRIPTION
	"The second output name of slave3"
    ::= { slave3OutputSwitch 19}
	
slave3OutputSwitchtwenty OBJECT-TYPE
    SYNTAX      DisplayString
    MAX-ACCESS  read-write
    STATUS      current
    DESCRIPTION
	"The second output name of slave3"
    ::= { slave3OutputSwitch 20}
	
slave3OutputSwitchTwentyone OBJECT-TYPE
    SYNTAX      DisplayString
    MAX-ACCESS  read-write
    STATUS      current
    DESCRIPTION
	"The second output name of slave3"
    ::= { slave3OutputSwitch 21}
	
slave3OutputSwitchTwentyonetwo OBJECT-TYPE
    SYNTAX      DisplayString
    MAX-ACCESS  read-write
    STATUS      current
    DESCRIPTION
	"The second output name of slave3"
    ::= { slave3OutputSwitch 22}
	
slave3OutputSwitchTwentythree OBJECT-TYPE
    SYNTAX      DisplayString
    MAX-ACCESS  read-write
    STATUS      current
    DESCRIPTION
	"The second output name of slave3"
    ::= { slave3OutputSwitch 23}
	
slave3OutputSwitchTwentyfour OBJECT-TYPE
    SYNTAX      DisplayString
    MAX-ACCESS  read-write
    STATUS      current
    DESCRIPTION
	"The second output name of slave3"
    ::= { slave3OutputSwitch 24}
	
slave3OutputSwitchTwentyfive OBJECT-TYPE
    SYNTAX      DisplayString
    MAX-ACCESS  read-write
    STATUS      current
    DESCRIPTION
	"The second output name of slave3"
    ::= { slave3OutputSwitch 25}
	
slave3OutputSwitchTwentysix OBJECT-TYPE
    SYNTAX      DisplayString
    MAX-ACCESS  read-write
    STATUS      current
    DESCRIPTION
	"The second output name of slave3"
    ::= { slave3OutputSwitch 26}
	
slave3OutputSwitchTwentyseven OBJECT-TYPE
    SYNTAX      DisplayString
    MAX-ACCESS  read-write
    STATUS      current
    DESCRIPTION
	"The second output name of slave3"
    ::= { slave3OutputSwitch 27}
	
slave3OutputSwitchTwentyeight OBJECT-TYPE
    SYNTAX      DisplayString
    MAX-ACCESS  read-write
    STATUS      current
    DESCRIPTION
	"The second output name of slave3"
    ::= { slave3OutputSwitch 28}	
slave3OutputSwitchTwentynine OBJECT-TYPE
    SYNTAX      DisplayString
    MAX-ACCESS  read-write
    STATUS      current
    DESCRIPTION
	"The second output name of slave3"
    ::= { slave3OutputSwitch 29}
	
slave3OutputSwitchThirty OBJECT-TYPE
    SYNTAX      DisplayString
    MAX-ACCESS  read-write
    STATUS      current
    DESCRIPTION
	"The second output name of slave3"
    ::= { slave3OutputSwitch 30}
	
slave3OutputSwitchThirtyone OBJECT-TYPE
    SYNTAX      DisplayString
    MAX-ACCESS  read-write
    STATUS      current
    DESCRIPTION
	"The second output name of slave3"
    ::= { slave3OutputSwitch 31}
	
slave3OutputSwitchThirtytwo OBJECT-TYPE
    SYNTAX      DisplayString
    MAX-ACCESS  read-write
    STATUS      current
    DESCRIPTION
	"The second output name of slave3"
    ::= { slave3OutputSwitch 32}
	
slave3OutputSwitchThirtythree OBJECT-TYPE
    SYNTAX      DisplayString
    MAX-ACCESS  read-write
    STATUS      current
    DESCRIPTION
	"The second output name of slave3"
    ::= { slave3OutputSwitch 33}
	
slave3OutputSwitchThirtyfour OBJECT-TYPE
    SYNTAX      DisplayString
    MAX-ACCESS  read-write
    STATUS      current
    DESCRIPTION
	"The second output name of slave3"
    ::= { slave3OutputSwitch 34}
	
slave3OutputSwitchThirtyfive OBJECT-TYPE
    SYNTAX      DisplayString
    MAX-ACCESS  read-write
    STATUS      current
    DESCRIPTION
	"The second output name of slave3"
    ::= { slave3OutputSwitch 35}
	
slave3OutputSwitchThirtysix OBJECT-TYPE
    SYNTAX      DisplayString
    MAX-ACCESS  read-write
    STATUS      current
    DESCRIPTION
	"The second output name of slave3"
    ::= { slave3OutputSwitch 36}
	
slave3OutputSwitchThirtyseven OBJECT-TYPE
    SYNTAX      DisplayString
    MAX-ACCESS  read-write
    STATUS      current
    DESCRIPTION
	"The second output name of slave3"
    ::= { slave3OutputSwitch 37}
	
slave3OutputSwitchThirtyeight OBJECT-TYPE
    SYNTAX      DisplayString
    MAX-ACCESS  read-write
    STATUS      current
    DESCRIPTION
	"The second output name of slave3"
    ::= { slave3OutputSwitch 38}
	
slave3OutputSwitchThirtynine OBJECT-TYPE
    SYNTAX      DisplayString
    MAX-ACCESS  read-write
    STATUS      current
    DESCRIPTION
	"The second output name of slave3"
    ::= { slave3OutputSwitch 39}
	
slave3OutputSwitchFourty OBJECT-TYPE
    SYNTAX      DisplayString
    MAX-ACCESS  read-write
    STATUS      current
    DESCRIPTION
	"The second output name of slave3"
    ::= { slave3OutputSwitch 40}
	
slave3OutputSwitchFourtyone OBJECT-TYPE
    SYNTAX      DisplayString
    MAX-ACCESS  read-write
    STATUS      current
    DESCRIPTION
	"The second output name of slave3"
    ::= { slave3OutputSwitch 41}
	
slave3OutputSwitchFourtytwo OBJECT-TYPE
    SYNTAX      DisplayString
    MAX-ACCESS  read-write
    STATUS      current
    DESCRIPTION
	"The second output name of slave3"
    ::= { slave3OutputSwitch 42}

	
-------------------------------slave3 output current------------------------	
slave3OutputCurrent OBJECT IDENTIFIER ::= { slave3 8}		
slave3OutputCurrentValue OBJECT IDENTIFIER ::= { slave3OutputCurrent 1}	

slave3OutputCurrentValueOne OBJECT-TYPE
    SYNTAX      DisplayString
    MAX-ACCESS  read-write
    STATUS      current
    DESCRIPTION
	"The first output name of slave3"
    ::= { slave3OutputCurrentValue 1}

slave3OutputCurrentValueTwo OBJECT-TYPE
    SYNTAX      DisplayString
    MAX-ACCESS  read-write
    STATUS      current
    DESCRIPTION
	"The second output name of slave3"
    ::= { slave3OutputCurrentValue 2}

slave3OutputCurrentValueThree OBJECT-TYPE
    SYNTAX      DisplayString
    MAX-ACCESS  read-write
    STATUS      current
    DESCRIPTION
	"The second output name of slave3"
    ::= { slave3OutputCurrentValue 3}

slave3OutputCurrentValueFour OBJECT-TYPE
    SYNTAX      DisplayString
    MAX-ACCESS  read-write
    STATUS      current
    DESCRIPTION
	"The second output name of slave3"
    ::= { slave3OutputCurrentValue 4}

slave3OutputCurrentValueFive OBJECT-TYPE
    SYNTAX      DisplayString
    MAX-ACCESS  read-write
    STATUS      current
    DESCRIPTION
	"The second output name of slave3"
    ::= { slave3OutputCurrentValue 5}

slave3OutputCurrentValueSix OBJECT-TYPE
    SYNTAX      DisplayString
    MAX-ACCESS  read-write
    STATUS      current
    DESCRIPTION
	"The second output name of slave3"
    ::= { slave3OutputCurrentValue 6}

slave3OutputCurrentValueSeven OBJECT-TYPE
    SYNTAX      DisplayString
    MAX-ACCESS  read-write
    STATUS      current
    DESCRIPTION
	"The second output name of slave3"
    ::= { slave3OutputCurrentValue 7}

slave3OutputCurrentValueEight OBJECT-TYPE
    SYNTAX      DisplayString
    MAX-ACCESS  read-write
    STATUS      current
    DESCRIPTION
	"The second output name of slave3"
    ::= { slave3OutputCurrentValue 8}

slave3OutputCurrentValueNine OBJECT-TYPE
    SYNTAX      DisplayString
    MAX-ACCESS  read-write
    STATUS      current
    DESCRIPTION
	"The second output name of slave3"
    ::= { slave3OutputCurrentValue 9}

slave3OutputCurrentValueTen OBJECT-TYPE
    SYNTAX      DisplayString
    MAX-ACCESS  read-write
    STATUS      current
    DESCRIPTION
	"The second output name of slave3"
    ::= { slave3OutputCurrentValue 10}

slave3OutputCurrentValueEleven OBJECT-TYPE
    SYNTAX      DisplayString
    MAX-ACCESS  read-write
    STATUS      current
    DESCRIPTION
	"The second output name of slave3"
    ::= { slave3OutputCurrentValue 11}

slave3OutputCurrentValueTwel OBJECT-TYPE
    SYNTAX      DisplayString
    MAX-ACCESS  read-write
    STATUS      current
    DESCRIPTION
	"The second output name of slave3"
    ::= { slave3OutputCurrentValue 12}

slave3OutputCurrentValueThirteen OBJECT-TYPE
    SYNTAX      DisplayString
    MAX-ACCESS  read-write
    STATUS      current
    DESCRIPTION
	"The second output name of slave3"
    ::= { slave3OutputCurrentValue 13}

slave3OutputCurrentValueFourteen OBJECT-TYPE
    SYNTAX      DisplayString
    MAX-ACCESS  read-write
    STATUS      current
    DESCRIPTION
	"The second output name of slave3"
    ::= { slave3OutputCurrentValue 14}

slave3OutputCurrentValueFifteen OBJECT-TYPE
    SYNTAX      DisplayString
    MAX-ACCESS  read-write
    STATUS      current
    DESCRIPTION
	"The second output name of slave3"
    ::= { slave3OutputCurrentValue 15}

slave3OutputCurrentValueSixteen OBJECT-TYPE
    SYNTAX      DisplayString
    MAX-ACCESS  read-write
    STATUS      current
    DESCRIPTION
	"The second output name of slave3"
    ::= { slave3OutputCurrentValue 16}

slave3OutputCurrentValueSeventeen OBJECT-TYPE
    SYNTAX      DisplayString
    MAX-ACCESS  read-write
    STATUS      current
    DESCRIPTION
	"The second output name of slave3"
    ::= { slave3OutputCurrentValue 17}

slave3OutputCurrentValueEighteen OBJECT-TYPE
    SYNTAX      DisplayString
    MAX-ACCESS  read-write
    STATUS      current
    DESCRIPTION
	"The second output name of slave3"
    ::= { slave3OutputCurrentValue 18}
	
slave3OutputCurrentValueNineteen OBJECT-TYPE
    SYNTAX      DisplayString
    MAX-ACCESS  read-write
    STATUS      current
    DESCRIPTION
	"The second output name of slave3"
    ::= { slave3OutputCurrentValue 19}
	
slave3OutputCurrentValuetwenty OBJECT-TYPE
    SYNTAX      DisplayString
    MAX-ACCESS  read-write
    STATUS      current
    DESCRIPTION
	"The second output name of slave3"
    ::= { slave3OutputCurrentValue 20}
	
slave3OutputCurrentValueTwentyone OBJECT-TYPE
    SYNTAX      DisplayString
    MAX-ACCESS  read-write
    STATUS      current
    DESCRIPTION
	"The second output name of slave3"
    ::= { slave3OutputCurrentValue 21}
	
slave3OutputCurrentValueTwentyonetwo OBJECT-TYPE
    SYNTAX      DisplayString
    MAX-ACCESS  read-write
    STATUS      current
    DESCRIPTION
	"The second output name of slave3"
    ::= { slave3OutputCurrentValue 22}
	
slave3OutputCurrentValueTwentythree OBJECT-TYPE
    SYNTAX      DisplayString
    MAX-ACCESS  read-write
    STATUS      current
    DESCRIPTION
	"The second output name of slave3"
    ::= { slave3OutputCurrentValue 23}
	
slave3OutputCurrentValueTwentyfour OBJECT-TYPE
    SYNTAX      DisplayString
    MAX-ACCESS  read-write
    STATUS      current
    DESCRIPTION
	"The second output name of slave3"
    ::= { slave3OutputCurrentValue 24}
	
slave3OutputCurrentValueTwentyfive OBJECT-TYPE
    SYNTAX      DisplayString
    MAX-ACCESS  read-write
    STATUS      current
    DESCRIPTION
	"The second output name of slave3"
    ::= { slave3OutputCurrentValue 25}
	
slave3OutputCurrentValueTwentysix OBJECT-TYPE
    SYNTAX      DisplayString
    MAX-ACCESS  read-write
    STATUS      current
    DESCRIPTION
	"The second output name of slave3"
    ::= { slave3OutputCurrentValue 26}
	
slave3OutputCurrentValueTwentyseven OBJECT-TYPE
    SYNTAX      DisplayString
    MAX-ACCESS  read-write
    STATUS      current
    DESCRIPTION
	"The second output name of slave3"
    ::= { slave3OutputCurrentValue 27}
	
slave3OutputCurrentValueTwentyeight OBJECT-TYPE
    SYNTAX      DisplayString
    MAX-ACCESS  read-write
    STATUS      current
    DESCRIPTION
	"The second output name of slave3"
    ::= { slave3OutputCurrentValue 28}	
slave3OutputCurrentValueTwentynine OBJECT-TYPE
    SYNTAX      DisplayString
    MAX-ACCESS  read-write
    STATUS      current
    DESCRIPTION
	"The second output name of slave3"
    ::= { slave3OutputCurrentValue 29}
	
slave3OutputCurrentValueThirty OBJECT-TYPE
    SYNTAX      DisplayString
    MAX-ACCESS  read-write
    STATUS      current
    DESCRIPTION
	"The second output name of slave3"
    ::= { slave3OutputCurrentValue 30}
	
slave3OutputCurrentValueThirtyone OBJECT-TYPE
    SYNTAX      DisplayString
    MAX-ACCESS  read-write
    STATUS      current
    DESCRIPTION
	"The second output name of slave3"
    ::= { slave3OutputCurrentValue 31}
	
slave3OutputCurrentValueThirtytwo OBJECT-TYPE
    SYNTAX      DisplayString
    MAX-ACCESS  read-write
    STATUS      current
    DESCRIPTION
	"The second output name of slave3"
    ::= { slave3OutputCurrentValue 32}
	
slave3OutputCurrentValueThirtythree OBJECT-TYPE
    SYNTAX      DisplayString
    MAX-ACCESS  read-write
    STATUS      current
    DESCRIPTION
	"The second output name of slave3"
    ::= { slave3OutputCurrentValue 33}
	
slave3OutputCurrentValueThirtyfour OBJECT-TYPE
    SYNTAX      DisplayString
    MAX-ACCESS  read-write
    STATUS      current
    DESCRIPTION
	"The second output name of slave3"
    ::= { slave3OutputCurrentValue 34}
	
slave3OutputCurrentValueThirtyfive OBJECT-TYPE
    SYNTAX      DisplayString
    MAX-ACCESS  read-write
    STATUS      current
    DESCRIPTION
	"The second output name of slave3"
    ::= { slave3OutputCurrentValue 35}
	
slave3OutputCurrentValueThirtysix OBJECT-TYPE
    SYNTAX      DisplayString
    MAX-ACCESS  read-write
    STATUS      current
    DESCRIPTION
	"The second output name of slave3"
    ::= { slave3OutputCurrentValue 36}
	
slave3OutputCurrentValueThirtyseven OBJECT-TYPE
    SYNTAX      DisplayString
    MAX-ACCESS  read-write
    STATUS      current
    DESCRIPTION
	"The second output name of slave3"
    ::= { slave3OutputCurrentValue 37}
	
slave3OutputCurrentValueThirtyeight OBJECT-TYPE
    SYNTAX      DisplayString
    MAX-ACCESS  read-write
    STATUS      current
    DESCRIPTION
	"The second output name of slave3"
    ::= { slave3OutputCurrentValue 38}
	
slave3OutputCurrentValueThirtynine OBJECT-TYPE
    SYNTAX      DisplayString
    MAX-ACCESS  read-write
    STATUS      current
    DESCRIPTION
	"The second output name of slave3"
    ::= { slave3OutputCurrentValue 39}
	
slave3OutputCurrentValueFourty OBJECT-TYPE
    SYNTAX      DisplayString
    MAX-ACCESS  read-write
    STATUS      current
    DESCRIPTION
	"The second output name of slave3"
    ::= { slave3OutputCurrentValue 40}
	
slave3OutputCurrentValueFourtyone OBJECT-TYPE
    SYNTAX      DisplayString
    MAX-ACCESS  read-write
    STATUS      current
    DESCRIPTION
	"The second output name of slave3"
    ::= { slave3OutputCurrentValue 41}
	
slave3OutputCurrentValueFourtytwo OBJECT-TYPE
    SYNTAX      DisplayString
    MAX-ACCESS  read-write
    STATUS      current
    DESCRIPTION
	"The second output name of slave3"
    ::= { slave3OutputCurrentValue 42}


-------------------------------slave3 output current Min------------------------			
slave3OutputCurrentMin OBJECT IDENTIFIER ::= { slave3OutputCurrent 2}	

slave3OutputCurrentMinOne OBJECT-TYPE
    SYNTAX      DisplayString
    MAX-ACCESS  read-write
    STATUS      current
    DESCRIPTION
	"The first output Min. current alarm value of slave3"
    ::= { slave3OutputCurrentMin 1}

slave3OutputCurrentMinTwo OBJECT-TYPE
    SYNTAX      DisplayString
    MAX-ACCESS  read-write
    STATUS      current
    DESCRIPTION
	"The second output Min. current alarm value of slave3"
    ::= { slave3OutputCurrentMin 2}

slave3OutputCurrentMinThree OBJECT-TYPE
    SYNTAX      DisplayString
    MAX-ACCESS  read-write
    STATUS      current
    DESCRIPTION
	"The second output Min. current alarm value of slave3"
    ::= { slave3OutputCurrentMin 3}

slave3OutputCurrentMinFour OBJECT-TYPE
    SYNTAX      DisplayString
    MAX-ACCESS  read-write
    STATUS      current
    DESCRIPTION
	"The second output Min. current alarm value of slave3"
    ::= { slave3OutputCurrentMin 4}

slave3OutputCurrentMinFive OBJECT-TYPE
    SYNTAX      DisplayString
    MAX-ACCESS  read-write
    STATUS      current
    DESCRIPTION
	"The second output Min. current alarm value of slave3"
    ::= { slave3OutputCurrentMin 5}

slave3OutputCurrentMinSix OBJECT-TYPE
    SYNTAX      DisplayString
    MAX-ACCESS  read-write
    STATUS      current
    DESCRIPTION
	"The second output Min. current alarm value of slave3"
    ::= { slave3OutputCurrentMin 6}

slave3OutputCurrentMinSeven OBJECT-TYPE
    SYNTAX      DisplayString
    MAX-ACCESS  read-write
    STATUS      current
    DESCRIPTION
	"The second output Min. current alarm value of slave3"
    ::= { slave3OutputCurrentMin 7}

slave3OutputCurrentMinEight OBJECT-TYPE
    SYNTAX      DisplayString
    MAX-ACCESS  read-write
    STATUS      current
    DESCRIPTION
	"The second output Min. current alarm value of slave3"
    ::= { slave3OutputCurrentMin 8}

slave3OutputCurrentMinNine OBJECT-TYPE
    SYNTAX      DisplayString
    MAX-ACCESS  read-write
    STATUS      current
    DESCRIPTION
	"The second output Min. current alarm value of slave3"
    ::= { slave3OutputCurrentMin 9}

slave3OutputCurrentMinTen OBJECT-TYPE
    SYNTAX      DisplayString
    MAX-ACCESS  read-write
    STATUS      current
    DESCRIPTION
	"The second output Min. current alarm value of slave3"
    ::= { slave3OutputCurrentMin 10}

slave3OutputCurrentMinEleven OBJECT-TYPE
    SYNTAX      DisplayString
    MAX-ACCESS  read-write
    STATUS      current
    DESCRIPTION
	"The second output Min. current alarm value of slave3"
    ::= { slave3OutputCurrentMin 11}

slave3OutputCurrentMinTwel OBJECT-TYPE
    SYNTAX      DisplayString
    MAX-ACCESS  read-write
    STATUS      current
    DESCRIPTION
	"The second output Min. current alarm value of slave3"
    ::= { slave3OutputCurrentMin 12}

slave3OutputCurrentMinThirteen OBJECT-TYPE
    SYNTAX      DisplayString
    MAX-ACCESS  read-write
    STATUS      current
    DESCRIPTION
	"The second output Min. current alarm value of slave3"
    ::= { slave3OutputCurrentMin 13}

slave3OutputCurrentMinFourteen OBJECT-TYPE
    SYNTAX      DisplayString
    MAX-ACCESS  read-write
    STATUS      current
    DESCRIPTION
	"The second output Min. current alarm value of slave3"
    ::= { slave3OutputCurrentMin 14}

slave3OutputCurrentMinFifteen OBJECT-TYPE
    SYNTAX      DisplayString
    MAX-ACCESS  read-write
    STATUS      current
    DESCRIPTION
	"The second output Min. current alarm value of slave3"
    ::= { slave3OutputCurrentMin 15}

slave3OutputCurrentMinSixteen OBJECT-TYPE
    SYNTAX      DisplayString
    MAX-ACCESS  read-write
    STATUS      current
    DESCRIPTION
	"The second output Min. current alarm value of slave3"
    ::= { slave3OutputCurrentMin 16}

slave3OutputCurrentMinSeventeen OBJECT-TYPE
    SYNTAX      DisplayString
    MAX-ACCESS  read-write
    STATUS      current
    DESCRIPTION
	"The second output Min. current alarm value of slave3"
    ::= { slave3OutputCurrentMin 17}

slave3OutputCurrentMinEighteen OBJECT-TYPE
    SYNTAX      DisplayString
    MAX-ACCESS  read-write
    STATUS      current
    DESCRIPTION
	"The second output Min. current alarm value of slave3"
    ::= { slave3OutputCurrentMin 18}
	
slave3OutputCurrentMinNineteen OBJECT-TYPE
    SYNTAX      DisplayString
    MAX-ACCESS  read-write
    STATUS      current
    DESCRIPTION
	"The second output Min. current alarm value of slave3"
    ::= { slave3OutputCurrentMin 19}
	
slave3OutputCurrentMintwenty OBJECT-TYPE
    SYNTAX      DisplayString
    MAX-ACCESS  read-write
    STATUS      current
    DESCRIPTION
	"The second output Min. current alarm value of slave3"
    ::= { slave3OutputCurrentMin 20}
	
slave3OutputCurrentMinTwentyone OBJECT-TYPE
    SYNTAX      DisplayString
    MAX-ACCESS  read-write
    STATUS      current
    DESCRIPTION
	"The second output Min. current alarm value of slave3"
    ::= { slave3OutputCurrentMin 21}
	
slave3OutputCurrentMinTwentyonetwo OBJECT-TYPE
    SYNTAX      DisplayString
    MAX-ACCESS  read-write
    STATUS      current
    DESCRIPTION
	"The second output Min. current alarm value of slave3"
    ::= { slave3OutputCurrentMin 22}
	
slave3OutputCurrentMinTwentythree OBJECT-TYPE
    SYNTAX      DisplayString
    MAX-ACCESS  read-write
    STATUS      current
    DESCRIPTION
	"The second output Min. current alarm value of slave3"
    ::= { slave3OutputCurrentMin 23}
	
slave3OutputCurrentMinTwentyfour OBJECT-TYPE
    SYNTAX      DisplayString
    MAX-ACCESS  read-write
    STATUS      current
    DESCRIPTION
	"The second output Min. current alarm value of slave3"
    ::= { slave3OutputCurrentMin 24}
	
slave3OutputCurrentMinTwentyfive OBJECT-TYPE
    SYNTAX      DisplayString
    MAX-ACCESS  read-write
    STATUS      current
    DESCRIPTION
	"The second output Min. current alarm value of slave3"
    ::= { slave3OutputCurrentMin 25}
	
slave3OutputCurrentMinTwentysix OBJECT-TYPE
    SYNTAX      DisplayString
    MAX-ACCESS  read-write
    STATUS      current
    DESCRIPTION
	"The second output Min. current alarm value of slave3"
    ::= { slave3OutputCurrentMin 26}
	
slave3OutputCurrentMinTwentyseven OBJECT-TYPE
    SYNTAX      DisplayString
    MAX-ACCESS  read-write
    STATUS      current
    DESCRIPTION
	"The second output Min. current alarm value of slave3"
    ::= { slave3OutputCurrentMin 27}
	
slave3OutputCurrentMinTwentyeight OBJECT-TYPE
    SYNTAX      DisplayString
    MAX-ACCESS  read-write
    STATUS      current
    DESCRIPTION
	"The second output Min. current alarm value of slave3"
    ::= { slave3OutputCurrentMin 28}	
slave3OutputCurrentMinTwentynine OBJECT-TYPE
    SYNTAX      DisplayString
    MAX-ACCESS  read-write
    STATUS      current
    DESCRIPTION
	"The second output Min. current alarm value of slave3"
    ::= { slave3OutputCurrentMin 29}
	
slave3OutputCurrentMinThirty OBJECT-TYPE
    SYNTAX      DisplayString
    MAX-ACCESS  read-write
    STATUS      current
    DESCRIPTION
	"The second output Min. current alarm value of slave3"
    ::= { slave3OutputCurrentMin 30}
	
slave3OutputCurrentMinThirtyone OBJECT-TYPE
    SYNTAX      DisplayString
    MAX-ACCESS  read-write
    STATUS      current
    DESCRIPTION
	"The second output Min. current alarm value of slave3"
    ::= { slave3OutputCurrentMin 31}
	
slave3OutputCurrentMinThirtytwo OBJECT-TYPE
    SYNTAX      DisplayString
    MAX-ACCESS  read-write
    STATUS      current
    DESCRIPTION
	"The second output Min. current alarm value of slave3"
    ::= { slave3OutputCurrentMin 32}
	
slave3OutputCurrentMinThirtythree OBJECT-TYPE
    SYNTAX      DisplayString
    MAX-ACCESS  read-write
    STATUS      current
    DESCRIPTION
	"The second output Min. current alarm value of slave3"
    ::= { slave3OutputCurrentMin 33}
	
slave3OutputCurrentMinThirtyfour OBJECT-TYPE
    SYNTAX      DisplayString
    MAX-ACCESS  read-write
    STATUS      current
    DESCRIPTION
	"The second output Min. current alarm value of slave3"
    ::= { slave3OutputCurrentMin 34}
	
slave3OutputCurrentMinThirtyfive OBJECT-TYPE
    SYNTAX      DisplayString
    MAX-ACCESS  read-write
    STATUS      current
    DESCRIPTION
	"The second output Min. current alarm value of slave3"
    ::= { slave3OutputCurrentMin 35}
	
slave3OutputCurrentMinThirtysix OBJECT-TYPE
    SYNTAX      DisplayString
    MAX-ACCESS  read-write
    STATUS      current
    DESCRIPTION
	"The second output Min. current alarm value of slave3"
    ::= { slave3OutputCurrentMin 36}
	
slave3OutputCurrentMinThirtyseven OBJECT-TYPE
    SYNTAX      DisplayString
    MAX-ACCESS  read-write
    STATUS      current
    DESCRIPTION
	"The second output Min. current alarm value of slave3"
    ::= { slave3OutputCurrentMin 37}
	
slave3OutputCurrentMinThirtyeight OBJECT-TYPE
    SYNTAX      DisplayString
    MAX-ACCESS  read-write
    STATUS      current
    DESCRIPTION
	"The second output Min. current alarm value of slave3"
    ::= { slave3OutputCurrentMin 38}
	
slave3OutputCurrentMinThirtynine OBJECT-TYPE
    SYNTAX      DisplayString
    MAX-ACCESS  read-write
    STATUS      current
    DESCRIPTION
	"The second output Min. current alarm value of slave3"
    ::= { slave3OutputCurrentMin 39}
	
slave3OutputCurrentMinFourty OBJECT-TYPE
    SYNTAX      DisplayString
    MAX-ACCESS  read-write
    STATUS      current
    DESCRIPTION
	"The second output Min. current alarm value of slave3"
    ::= { slave3OutputCurrentMin 40}
	
slave3OutputCurrentMinFourtyone OBJECT-TYPE
    SYNTAX      DisplayString
    MAX-ACCESS  read-write
    STATUS      current
    DESCRIPTION
	"The second output Min. current alarm value of slave3"
    ::= { slave3OutputCurrentMin 41}
	
slave3OutputCurrentMinFourtytwo OBJECT-TYPE
    SYNTAX      DisplayString
    MAX-ACCESS  read-write
    STATUS      current
    DESCRIPTION
	"The second output Min. current alarm value of slave3"
    ::= { slave3OutputCurrentMin 42}


------------------------slave3 output current Min critical----------------			
slave3OutputCurrentMinCritical OBJECT IDENTIFIER ::= { slave3OutputCurrent 3}	

slave3OutputCurrentMinCriticalOne OBJECT-TYPE
    SYNTAX      DisplayString
    MAX-ACCESS  read-write
    STATUS      current
    DESCRIPTION
	"The first output Min. current warning value of slave3"
    ::= { slave3OutputCurrentMinCritical 1}

slave3OutputCurrentMinCriticalTwo OBJECT-TYPE
    SYNTAX      DisplayString
    MAX-ACCESS  read-write
    STATUS      current
    DESCRIPTION
	"The second output Min. current warning value of slave3"
    ::= { slave3OutputCurrentMinCritical 2}

slave3OutputCurrentMinCriticalThree OBJECT-TYPE
    SYNTAX      DisplayString
    MAX-ACCESS  read-write
    STATUS      current
    DESCRIPTION
	"The second output Min. current warning value of slave3"
    ::= { slave3OutputCurrentMinCritical 3}

slave3OutputCurrentMinCriticalFour OBJECT-TYPE
    SYNTAX      DisplayString
    MAX-ACCESS  read-write
    STATUS      current
    DESCRIPTION
	"The second output Min. current warning value of slave3"
    ::= { slave3OutputCurrentMinCritical 4}

slave3OutputCurrentMinCriticalFive OBJECT-TYPE
    SYNTAX      DisplayString
    MAX-ACCESS  read-write
    STATUS      current
    DESCRIPTION
	"The second output Min. current warning value of slave3"
    ::= { slave3OutputCurrentMinCritical 5}

slave3OutputCurrentMinCriticalSix OBJECT-TYPE
    SYNTAX      DisplayString
    MAX-ACCESS  read-write
    STATUS      current
    DESCRIPTION
	"The second output Min. current warning value of slave3"
    ::= { slave3OutputCurrentMinCritical 6}

slave3OutputCurrentMinCriticalSeven OBJECT-TYPE
    SYNTAX      DisplayString
    MAX-ACCESS  read-write
    STATUS      current
    DESCRIPTION
	"The second output Min. current warning value of slave3"
    ::= { slave3OutputCurrentMinCritical 7}

slave3OutputCurrentMinCriticalEight OBJECT-TYPE
    SYNTAX      DisplayString
    MAX-ACCESS  read-write
    STATUS      current
    DESCRIPTION
	"The second output Min. current warning value of slave3"
    ::= { slave3OutputCurrentMinCritical 8}

slave3OutputCurrentMinCriticalNine OBJECT-TYPE
    SYNTAX      DisplayString
    MAX-ACCESS  read-write
    STATUS      current
    DESCRIPTION
	"The second output Min. current warning value of slave3"
    ::= { slave3OutputCurrentMinCritical 9}

slave3OutputCurrentMinCriticalTen OBJECT-TYPE
    SYNTAX      DisplayString
    MAX-ACCESS  read-write
    STATUS      current
    DESCRIPTION
	"The second output Min. current warning value of slave3"
    ::= { slave3OutputCurrentMinCritical 10}

slave3OutputCurrentMinCriticalEleven OBJECT-TYPE
    SYNTAX      DisplayString
    MAX-ACCESS  read-write
    STATUS      current
    DESCRIPTION
	"The second output Min. current warning value of slave3"
    ::= { slave3OutputCurrentMinCritical 11}

slave3OutputCurrentMinCriticalTwel OBJECT-TYPE
    SYNTAX      DisplayString
    MAX-ACCESS  read-write
    STATUS      current
    DESCRIPTION
	"The second output Min. current warning value of slave3"
    ::= { slave3OutputCurrentMinCritical 12}

slave3OutputCurrentMinCriticalThirteen OBJECT-TYPE
    SYNTAX      DisplayString
    MAX-ACCESS  read-write
    STATUS      current
    DESCRIPTION
	"The second output Min. current warning value of slave3"
    ::= { slave3OutputCurrentMinCritical 13}

slave3OutputCurrentMinCriticalFourteen OBJECT-TYPE
    SYNTAX      DisplayString
    MAX-ACCESS  read-write
    STATUS      current
    DESCRIPTION
	"The second output Min. current warning value of slave3"
    ::= { slave3OutputCurrentMinCritical 14}

slave3OutputCurrentMinCriticalFifteen OBJECT-TYPE
    SYNTAX      DisplayString
    MAX-ACCESS  read-write
    STATUS      current
    DESCRIPTION
	"The second output Min. current warning value of slave3"
    ::= { slave3OutputCurrentMinCritical 15}

slave3OutputCurrentMinCriticalSixteen OBJECT-TYPE
    SYNTAX      DisplayString
    MAX-ACCESS  read-write
    STATUS      current
    DESCRIPTION
	"The second output Min. current warning value of slave3"
    ::= { slave3OutputCurrentMinCritical 16}

slave3OutputCurrentMinCriticalSeventeen OBJECT-TYPE
    SYNTAX      DisplayString
    MAX-ACCESS  read-write
    STATUS      current
    DESCRIPTION
	"The second output Min. current warning value of slave3"
    ::= { slave3OutputCurrentMinCritical 17}

slave3OutputCurrentMinCriticalEighteen OBJECT-TYPE
    SYNTAX      DisplayString
    MAX-ACCESS  read-write
    STATUS      current
    DESCRIPTION
	"The second output Min. current warning value of slave3"
    ::= { slave3OutputCurrentMinCritical 18}
	
slave3OutputCurrentMinCriticalNineteen OBJECT-TYPE
    SYNTAX      DisplayString
    MAX-ACCESS  read-write
    STATUS      current
    DESCRIPTION
	"The second output Min. current warning value of slave3"
    ::= { slave3OutputCurrentMinCritical 19}
	
slave3OutputCurrentMinCriticaltwenty OBJECT-TYPE
    SYNTAX      DisplayString
    MAX-ACCESS  read-write
    STATUS      current
    DESCRIPTION
	"The second output Min. current warning value of slave3"
    ::= { slave3OutputCurrentMinCritical 20}
	
slave3OutputCurrentMinCriticalTwentyone OBJECT-TYPE
    SYNTAX      DisplayString
    MAX-ACCESS  read-write
    STATUS      current
    DESCRIPTION
	"The second output Min. current warning value of slave3"
    ::= { slave3OutputCurrentMinCritical 21}
	
slave3OutputCurrentMinCriticalTwentyonetwo OBJECT-TYPE
    SYNTAX      DisplayString
    MAX-ACCESS  read-write
    STATUS      current
    DESCRIPTION
	"The second output Min. current warning value of slave3"
    ::= { slave3OutputCurrentMinCritical 22}
	
slave3OutputCurrentMinCriticalTwentythree OBJECT-TYPE
    SYNTAX      DisplayString
    MAX-ACCESS  read-write
    STATUS      current
    DESCRIPTION
	"The second output Min. current warning value of slave3"
    ::= { slave3OutputCurrentMinCritical 23}
	
slave3OutputCurrentMinCriticalTwentyfour OBJECT-TYPE
    SYNTAX      DisplayString
    MAX-ACCESS  read-write
    STATUS      current
    DESCRIPTION
	"The second output Min. current warning value of slave3"
    ::= { slave3OutputCurrentMinCritical 24}
	
slave3OutputCurrentMinCriticalTwentyfive OBJECT-TYPE
    SYNTAX      DisplayString
    MAX-ACCESS  read-write
    STATUS      current
    DESCRIPTION
	"The second output Min. current warning value of slave3"
    ::= { slave3OutputCurrentMinCritical 25}
	
slave3OutputCurrentMinCriticalTwentysix OBJECT-TYPE
    SYNTAX      DisplayString
    MAX-ACCESS  read-write
    STATUS      current
    DESCRIPTION
	"The second output Min. current warning value of slave3"
    ::= { slave3OutputCurrentMinCritical 26}
	
slave3OutputCurrentMinCriticalTwentyseven OBJECT-TYPE
    SYNTAX      DisplayString
    MAX-ACCESS  read-write
    STATUS      current
    DESCRIPTION
	"The second output Min. current warning value of slave3"
    ::= { slave3OutputCurrentMinCritical 27}
	
slave3OutputCurrentMinCriticalTwentyeight OBJECT-TYPE
    SYNTAX      DisplayString
    MAX-ACCESS  read-write
    STATUS      current
    DESCRIPTION
	"The second output Min. current warning value of slave3"
    ::= { slave3OutputCurrentMinCritical 28}	
slave3OutputCurrentMinCriticalTwentynine OBJECT-TYPE
    SYNTAX      DisplayString
    MAX-ACCESS  read-write
    STATUS      current
    DESCRIPTION
	"The second output Min. current warning value of slave3"
    ::= { slave3OutputCurrentMinCritical 29}
	
slave3OutputCurrentMinCriticalThirty OBJECT-TYPE
    SYNTAX      DisplayString
    MAX-ACCESS  read-write
    STATUS      current
    DESCRIPTION
	"The second output Min. current warning value of slave3"
    ::= { slave3OutputCurrentMinCritical 30}
	
slave3OutputCurrentMinCriticalThirtyone OBJECT-TYPE
    SYNTAX      DisplayString
    MAX-ACCESS  read-write
    STATUS      current
    DESCRIPTION
	"The second output Min. current warning value of slave3"
    ::= { slave3OutputCurrentMinCritical 31}
	
slave3OutputCurrentMinCriticalThirtytwo OBJECT-TYPE
    SYNTAX      DisplayString
    MAX-ACCESS  read-write
    STATUS      current
    DESCRIPTION
	"The second output Min. current warning value of slave3"
    ::= { slave3OutputCurrentMinCritical 32}
	
slave3OutputCurrentMinCriticalThirtythree OBJECT-TYPE
    SYNTAX      DisplayString
    MAX-ACCESS  read-write
    STATUS      current
    DESCRIPTION
	"The second output Min. current warning value of slave3"
    ::= { slave3OutputCurrentMinCritical 33}
	
slave3OutputCurrentMinCriticalThirtyfour OBJECT-TYPE
    SYNTAX      DisplayString
    MAX-ACCESS  read-write
    STATUS      current
    DESCRIPTION
	"The second output Min. current warning value of slave3"
    ::= { slave3OutputCurrentMinCritical 34}
	
slave3OutputCurrentMinCriticalThirtyfive OBJECT-TYPE
    SYNTAX      DisplayString
    MAX-ACCESS  read-write
    STATUS      current
    DESCRIPTION
	"The second output Min. current warning value of slave3"
    ::= { slave3OutputCurrentMinCritical 35}
	
slave3OutputCurrentMinCriticalThirtysix OBJECT-TYPE
    SYNTAX      DisplayString
    MAX-ACCESS  read-write
    STATUS      current
    DESCRIPTION
	"The second output Min. current warning value of slave3"
    ::= { slave3OutputCurrentMinCritical 36}
	
slave3OutputCurrentMinCriticalThirtyseven OBJECT-TYPE
    SYNTAX      DisplayString
    MAX-ACCESS  read-write
    STATUS      current
    DESCRIPTION
	"The second output Min. current warning value of slave3"
    ::= { slave3OutputCurrentMinCritical 37}
	
slave3OutputCurrentMinCriticalThirtyeight OBJECT-TYPE
    SYNTAX      DisplayString
    MAX-ACCESS  read-write
    STATUS      current
    DESCRIPTION
	"The second output Min. current warning value of slave3"
    ::= { slave3OutputCurrentMinCritical 38}
	
slave3OutputCurrentMinCriticalThirtynine OBJECT-TYPE
    SYNTAX      DisplayString
    MAX-ACCESS  read-write
    STATUS      current
    DESCRIPTION
	"The second output Min. current warning value of slave3"
    ::= { slave3OutputCurrentMinCritical 39}
	
slave3OutputCurrentMinCriticalFourty OBJECT-TYPE
    SYNTAX      DisplayString
    MAX-ACCESS  read-write
    STATUS      current
    DESCRIPTION
	"The second output Min. current warning value of slave3"
    ::= { slave3OutputCurrentMinCritical 40}
	
slave3OutputCurrentMinCriticalFourtyone OBJECT-TYPE
    SYNTAX      DisplayString
    MAX-ACCESS  read-write
    STATUS      current
    DESCRIPTION
	"The second output Min. current warning value of slave3"
    ::= { slave3OutputCurrentMinCritical 41}
	
slave3OutputCurrentMinCriticalFourtytwo OBJECT-TYPE
    SYNTAX      DisplayString
    MAX-ACCESS  read-write
    STATUS      current
    DESCRIPTION
	"The second output Min. current warning value of slave3"
    ::= { slave3OutputCurrentMinCritical 42}
	
	
------------------------slave3 output current Max critical----------------			
slave3OutputCurrentMaxCritical OBJECT IDENTIFIER ::= { slave3OutputCurrent 4}	

slave3OutputCurrentMaxCriticalOne OBJECT-TYPE
    SYNTAX      DisplayString
    MAX-ACCESS  read-write
    STATUS      current
    DESCRIPTION
	"The first output Max. current warning value of slave3"
    ::= { slave3OutputCurrentMaxCritical 1}

slave3OutputCurrentMaxCriticalTwo OBJECT-TYPE
    SYNTAX      DisplayString
    MAX-ACCESS  read-write
    STATUS      current
    DESCRIPTION
	"The second output Max. current warning value of slave3"
    ::= { slave3OutputCurrentMaxCritical 2}

slave3OutputCurrentMaxCriticalThree OBJECT-TYPE
    SYNTAX      DisplayString
    MAX-ACCESS  read-write
    STATUS      current
    DESCRIPTION
	"The second output Max. current warning value of slave3"
    ::= { slave3OutputCurrentMaxCritical 3}

slave3OutputCurrentMaxCriticalFour OBJECT-TYPE
    SYNTAX      DisplayString
    MAX-ACCESS  read-write
    STATUS      current
    DESCRIPTION
	"The second output Max. current warning value of slave3"
    ::= { slave3OutputCurrentMaxCritical 4}

slave3OutputCurrentMaxCriticalFive OBJECT-TYPE
    SYNTAX      DisplayString
    MAX-ACCESS  read-write
    STATUS      current
    DESCRIPTION
	"The second output Max. current warning value of slave3"
    ::= { slave3OutputCurrentMaxCritical 5}

slave3OutputCurrentMaxCriticalSix OBJECT-TYPE
    SYNTAX      DisplayString
    MAX-ACCESS  read-write
    STATUS      current
    DESCRIPTION
	"The second output Max. current warning value of slave3"
    ::= { slave3OutputCurrentMaxCritical 6}

slave3OutputCurrentMaxCriticalSeven OBJECT-TYPE
    SYNTAX      DisplayString
    MAX-ACCESS  read-write
    STATUS      current
    DESCRIPTION
	"The second output Max. current warning value of slave3"
    ::= { slave3OutputCurrentMaxCritical 7}

slave3OutputCurrentMaxCriticalEight OBJECT-TYPE
    SYNTAX      DisplayString
    MAX-ACCESS  read-write
    STATUS      current
    DESCRIPTION
	"The second output Max. current warning value of slave3"
    ::= { slave3OutputCurrentMaxCritical 8}

slave3OutputCurrentMaxCriticalNine OBJECT-TYPE
    SYNTAX      DisplayString
    MAX-ACCESS  read-write
    STATUS      current
    DESCRIPTION
	"The second output Max. current warning value of slave3"
    ::= { slave3OutputCurrentMaxCritical 9}

slave3OutputCurrentMaxCriticalTen OBJECT-TYPE
    SYNTAX      DisplayString
    MAX-ACCESS  read-write
    STATUS      current
    DESCRIPTION
	"The second output Max. current warning value of slave3"
    ::= { slave3OutputCurrentMaxCritical 10}

slave3OutputCurrentMaxCriticalEleven OBJECT-TYPE
    SYNTAX      DisplayString
    MAX-ACCESS  read-write
    STATUS      current
    DESCRIPTION
	"The second output Max. current warning value of slave3"
    ::= { slave3OutputCurrentMaxCritical 11}

slave3OutputCurrentMaxCriticalTwel OBJECT-TYPE
    SYNTAX      DisplayString
    MAX-ACCESS  read-write
    STATUS      current
    DESCRIPTION
	"The second output Max. current warning value of slave3"
    ::= { slave3OutputCurrentMaxCritical 12}

slave3OutputCurrentMaxCriticalThirteen OBJECT-TYPE
    SYNTAX      DisplayString
    MAX-ACCESS  read-write
    STATUS      current
    DESCRIPTION
	"The second output Max. current warning value of slave3"
    ::= { slave3OutputCurrentMaxCritical 13}

slave3OutputCurrentMaxCriticalFourteen OBJECT-TYPE
    SYNTAX      DisplayString
    MAX-ACCESS  read-write
    STATUS      current
    DESCRIPTION
	"The second output Max. current warning value of slave3"
    ::= { slave3OutputCurrentMaxCritical 14}

slave3OutputCurrentMaxCriticalFifteen OBJECT-TYPE
    SYNTAX      DisplayString
    MAX-ACCESS  read-write
    STATUS      current
    DESCRIPTION
	"The second output Max. current warning value of slave3"
    ::= { slave3OutputCurrentMaxCritical 15}

slave3OutputCurrentMaxCriticalSixteen OBJECT-TYPE
    SYNTAX      DisplayString
    MAX-ACCESS  read-write
    STATUS      current
    DESCRIPTION
	"The second output Max. current warning value of slave3"
    ::= { slave3OutputCurrentMaxCritical 16}

slave3OutputCurrentMaxCriticalSeventeen OBJECT-TYPE
    SYNTAX      DisplayString
    MAX-ACCESS  read-write
    STATUS      current
    DESCRIPTION
	"The second output Max. current warning value of slave3"
    ::= { slave3OutputCurrentMaxCritical 17}

slave3OutputCurrentMaxCriticalEighteen OBJECT-TYPE
    SYNTAX      DisplayString
    MAX-ACCESS  read-write
    STATUS      current
    DESCRIPTION
	"The second output Max. current warning value of slave3"
    ::= { slave3OutputCurrentMaxCritical 18}
	
slave3OutputCurrentMaxCriticalNineteen OBJECT-TYPE
    SYNTAX      DisplayString
    MAX-ACCESS  read-write
    STATUS      current
    DESCRIPTION
	"The second output Max. current warning value of slave3"
    ::= { slave3OutputCurrentMaxCritical 19}
	
slave3OutputCurrentMaxCriticaltwenty OBJECT-TYPE
    SYNTAX      DisplayString
    MAX-ACCESS  read-write
    STATUS      current
    DESCRIPTION
	"The second output Max. current warning value of slave3"
    ::= { slave3OutputCurrentMaxCritical 20}
	
slave3OutputCurrentMaxCriticalTwentyone OBJECT-TYPE
    SYNTAX      DisplayString
    MAX-ACCESS  read-write
    STATUS      current
    DESCRIPTION
	"The second output Max. current warning value of slave3"
    ::= { slave3OutputCurrentMaxCritical 21}
	
slave3OutputCurrentMaxCriticalTwentyonetwo OBJECT-TYPE
    SYNTAX      DisplayString
    MAX-ACCESS  read-write
    STATUS      current
    DESCRIPTION
	"The second output Max. current warning value of slave3"
    ::= { slave3OutputCurrentMaxCritical 22}
	
slave3OutputCurrentMaxCriticalTwentythree OBJECT-TYPE
    SYNTAX      DisplayString
    MAX-ACCESS  read-write
    STATUS      current
    DESCRIPTION
	"The second output Max. current warning value of slave3"
    ::= { slave3OutputCurrentMaxCritical 23}
	
slave3OutputCurrentMaxCriticalTwentyfour OBJECT-TYPE
    SYNTAX      DisplayString
    MAX-ACCESS  read-write
    STATUS      current
    DESCRIPTION
	"The second output Max. current warning value of slave3"
    ::= { slave3OutputCurrentMaxCritical 24}
	
slave3OutputCurrentMaxCriticalTwentyfive OBJECT-TYPE
    SYNTAX      DisplayString
    MAX-ACCESS  read-write
    STATUS      current
    DESCRIPTION
	"The second output Max. current warning value of slave3"
    ::= { slave3OutputCurrentMaxCritical 25}
	
slave3OutputCurrentMaxCriticalTwentysix OBJECT-TYPE
    SYNTAX      DisplayString
    MAX-ACCESS  read-write
    STATUS      current
    DESCRIPTION
	"The second output Max. current warning value of slave3"
    ::= { slave3OutputCurrentMaxCritical 26}
	
slave3OutputCurrentMaxCriticalTwentyseven OBJECT-TYPE
    SYNTAX      DisplayString
    MAX-ACCESS  read-write
    STATUS      current
    DESCRIPTION
	"The second output Max. current warning value of slave3"
    ::= { slave3OutputCurrentMaxCritical 27}
	
slave3OutputCurrentMaxCriticalTwentyeight OBJECT-TYPE
    SYNTAX      DisplayString
    MAX-ACCESS  read-write
    STATUS      current
    DESCRIPTION
	"The second output Max. current warning value of slave3"
    ::= { slave3OutputCurrentMaxCritical 28}	
slave3OutputCurrentMaxCriticalTwentynine OBJECT-TYPE
    SYNTAX      DisplayString
    MAX-ACCESS  read-write
    STATUS      current
    DESCRIPTION
	"The second output Max. current warning value of slave3"
    ::= { slave3OutputCurrentMaxCritical 29}
	
slave3OutputCurrentMaxCriticalThirty OBJECT-TYPE
    SYNTAX      DisplayString
    MAX-ACCESS  read-write
    STATUS      current
    DESCRIPTION
	"The second output Max. current warning value of slave3"
    ::= { slave3OutputCurrentMaxCritical 30}
	
slave3OutputCurrentMaxCriticalThirtyone OBJECT-TYPE
    SYNTAX      DisplayString
    MAX-ACCESS  read-write
    STATUS      current
    DESCRIPTION
	"The second output Max. current warning value of slave3"
    ::= { slave3OutputCurrentMaxCritical 31}
	
slave3OutputCurrentMaxCriticalThirtytwo OBJECT-TYPE
    SYNTAX      DisplayString
    MAX-ACCESS  read-write
    STATUS      current
    DESCRIPTION
	"The second output Max. current warning value of slave3"
    ::= { slave3OutputCurrentMaxCritical 32}
	
slave3OutputCurrentMaxCriticalThirtythree OBJECT-TYPE
    SYNTAX      DisplayString
    MAX-ACCESS  read-write
    STATUS      current
    DESCRIPTION
	"The second output Max. current warning value of slave3"
    ::= { slave3OutputCurrentMaxCritical 33}
	
slave3OutputCurrentMaxCriticalThirtyfour OBJECT-TYPE
    SYNTAX      DisplayString
    MAX-ACCESS  read-write
    STATUS      current
    DESCRIPTION
	"The second output Max. current warning value of slave3"
    ::= { slave3OutputCurrentMaxCritical 34}
	
slave3OutputCurrentMaxCriticalThirtyfive OBJECT-TYPE
    SYNTAX      DisplayString
    MAX-ACCESS  read-write
    STATUS      current
    DESCRIPTION
	"The second output Max. current warning value of slave3"
    ::= { slave3OutputCurrentMaxCritical 35}
	
slave3OutputCurrentMaxCriticalThirtysix OBJECT-TYPE
    SYNTAX      DisplayString
    MAX-ACCESS  read-write
    STATUS      current
    DESCRIPTION
	"The second output Max. current warning value of slave3"
    ::= { slave3OutputCurrentMaxCritical 36}
	
slave3OutputCurrentMaxCriticalThirtyseven OBJECT-TYPE
    SYNTAX      DisplayString
    MAX-ACCESS  read-write
    STATUS      current
    DESCRIPTION
	"The second output Max. current warning value of slave3"
    ::= { slave3OutputCurrentMaxCritical 37}
	
slave3OutputCurrentMaxCriticalThirtyeight OBJECT-TYPE
    SYNTAX      DisplayString
    MAX-ACCESS  read-write
    STATUS      current
    DESCRIPTION
	"The second output Max. current warning value of slave3"
    ::= { slave3OutputCurrentMaxCritical 38}
	
slave3OutputCurrentMaxCriticalThirtynine OBJECT-TYPE
    SYNTAX      DisplayString
    MAX-ACCESS  read-write
    STATUS      current
    DESCRIPTION
	"The second output Max. current warning value of slave3"
    ::= { slave3OutputCurrentMaxCritical 39}
	
slave3OutputCurrentMaxCriticalFourty OBJECT-TYPE
    SYNTAX      DisplayString
    MAX-ACCESS  read-write
    STATUS      current
    DESCRIPTION
	"The second output Max. current warning value of slave3"
    ::= { slave3OutputCurrentMaxCritical 40}
	
slave3OutputCurrentMaxCriticalFourtyone OBJECT-TYPE
    SYNTAX      DisplayString
    MAX-ACCESS  read-write
    STATUS      current
    DESCRIPTION
	"The second output Max. current warning value of slave3"
    ::= { slave3OutputCurrentMaxCritical 41}
	
slave3OutputCurrentMaxCriticalFourtytwo OBJECT-TYPE
    SYNTAX      DisplayString
    MAX-ACCESS  read-write
    STATUS      current
    DESCRIPTION
	"The second output Max. current warning value of slave3"
    ::= { slave3OutputCurrentMaxCritical 42}
	
	
------------------------slave3 output current Max----------------			
slave3OutputCurrentMax OBJECT IDENTIFIER ::= { slave3OutputCurrent 5}
	
slave3OutputCurrentMaxOne OBJECT-TYPE
    SYNTAX      DisplayString
    MAX-ACCESS  read-write
    STATUS      current
    DESCRIPTION
	"The first output Max. current alarm value of slave3"
    ::= { slave3OutputCurrentMax 1}

slave3OutputCurrentMaxTwo OBJECT-TYPE
    SYNTAX      DisplayString
    MAX-ACCESS  read-write
    STATUS      current
    DESCRIPTION
	"The second output Max. current alarm value of slave3"
    ::= { slave3OutputCurrentMax 2}

slave3OutputCurrentMaxThree OBJECT-TYPE
    SYNTAX      DisplayString
    MAX-ACCESS  read-write
    STATUS      current
    DESCRIPTION
	"The second output Max. current alarm value of slave3"
    ::= { slave3OutputCurrentMax 3}

slave3OutputCurrentMaxFour OBJECT-TYPE
    SYNTAX      DisplayString
    MAX-ACCESS  read-write
    STATUS      current
    DESCRIPTION
	"The second output Max. current alarm value of slave3"
    ::= { slave3OutputCurrentMax 4}

slave3OutputCurrentMaxFive OBJECT-TYPE
    SYNTAX      DisplayString
    MAX-ACCESS  read-write
    STATUS      current
    DESCRIPTION
	"The second output Max. current alarm value of slave3"
    ::= { slave3OutputCurrentMax 5}

slave3OutputCurrentMaxSix OBJECT-TYPE
    SYNTAX      DisplayString
    MAX-ACCESS  read-write
    STATUS      current
    DESCRIPTION
	"The second output Max. current alarm value of slave3"
    ::= { slave3OutputCurrentMax 6}

slave3OutputCurrentMaxSeven OBJECT-TYPE
    SYNTAX      DisplayString
    MAX-ACCESS  read-write
    STATUS      current
    DESCRIPTION
	"The second output Max. current alarm value of slave3"
    ::= { slave3OutputCurrentMax 7}

slave3OutputCurrentMaxEight OBJECT-TYPE
    SYNTAX      DisplayString
    MAX-ACCESS  read-write
    STATUS      current
    DESCRIPTION
	"The second output Max. current alarm value of slave3"
    ::= { slave3OutputCurrentMax 8}

slave3OutputCurrentMaxNine OBJECT-TYPE
    SYNTAX      DisplayString
    MAX-ACCESS  read-write
    STATUS      current
    DESCRIPTION
	"The second output Max. current alarm value of slave3"
    ::= { slave3OutputCurrentMax 9}

slave3OutputCurrentMaxTen OBJECT-TYPE
    SYNTAX      DisplayString
    MAX-ACCESS  read-write
    STATUS      current
    DESCRIPTION
	"The second output Max. current alarm value of slave3"
    ::= { slave3OutputCurrentMax 10}

slave3OutputCurrentMaxEleven OBJECT-TYPE
    SYNTAX      DisplayString
    MAX-ACCESS  read-write
    STATUS      current
    DESCRIPTION
	"The second output Max. current alarm value of slave3"
    ::= { slave3OutputCurrentMax 11}

slave3OutputCurrentMaxTwel OBJECT-TYPE
    SYNTAX      DisplayString
    MAX-ACCESS  read-write
    STATUS      current
    DESCRIPTION
	"The second output Max. current alarm value of slave3"
    ::= { slave3OutputCurrentMax 12}

slave3OutputCurrentMaxThirteen OBJECT-TYPE
    SYNTAX      DisplayString
    MAX-ACCESS  read-write
    STATUS      current
    DESCRIPTION
	"The second output Max. current alarm value of slave3"
    ::= { slave3OutputCurrentMax 13}

slave3OutputCurrentMaxFourteen OBJECT-TYPE
    SYNTAX      DisplayString
    MAX-ACCESS  read-write
    STATUS      current
    DESCRIPTION
	"The second output Max. current alarm value of slave3"
    ::= { slave3OutputCurrentMax 14}

slave3OutputCurrentMaxFifteen OBJECT-TYPE
    SYNTAX      DisplayString
    MAX-ACCESS  read-write
    STATUS      current
    DESCRIPTION
	"The second output Max. current alarm value of slave3"
    ::= { slave3OutputCurrentMax 15}

slave3OutputCurrentMaxSixteen OBJECT-TYPE
    SYNTAX      DisplayString
    MAX-ACCESS  read-write
    STATUS      current
    DESCRIPTION
	"The second output Max. current alarm value of slave3"
    ::= { slave3OutputCurrentMax 16}

slave3OutputCurrentMaxSeventeen OBJECT-TYPE
    SYNTAX      DisplayString
    MAX-ACCESS  read-write
    STATUS      current
    DESCRIPTION
	"The second output Max. current alarm value of slave3"
    ::= { slave3OutputCurrentMax 17}

slave3OutputCurrentMaxEighteen OBJECT-TYPE
    SYNTAX      DisplayString
    MAX-ACCESS  read-write
    STATUS      current
    DESCRIPTION
	"The second output Max. current alarm value of slave3"
    ::= { slave3OutputCurrentMax 18}
	
slave3OutputCurrentMaxNineteen OBJECT-TYPE
    SYNTAX      DisplayString
    MAX-ACCESS  read-write
    STATUS      current
    DESCRIPTION
	"The second output Max. current alarm value of slave3"
    ::= { slave3OutputCurrentMax 19}
	
slave3OutputCurrentMaxtwenty OBJECT-TYPE
    SYNTAX      DisplayString
    MAX-ACCESS  read-write
    STATUS      current
    DESCRIPTION
	"The second output Max. current alarm value of slave3"
    ::= { slave3OutputCurrentMax 20}
	
slave3OutputCurrentMaxTwentyone OBJECT-TYPE
    SYNTAX      DisplayString
    MAX-ACCESS  read-write
    STATUS      current
    DESCRIPTION
	"The second output Max. current alarm value of slave3"
    ::= { slave3OutputCurrentMax 21}
	
slave3OutputCurrentMaxTwentyonetwo OBJECT-TYPE
    SYNTAX      DisplayString
    MAX-ACCESS  read-write
    STATUS      current
    DESCRIPTION
	"The second output Max. current alarm value of slave3"
    ::= { slave3OutputCurrentMax 22}
	
slave3OutputCurrentMaxTwentythree OBJECT-TYPE
    SYNTAX      DisplayString
    MAX-ACCESS  read-write
    STATUS      current
    DESCRIPTION
	"The second output Max. current alarm value of slave3"
    ::= { slave3OutputCurrentMax 23}
	
slave3OutputCurrentMaxTwentyfour OBJECT-TYPE
    SYNTAX      DisplayString
    MAX-ACCESS  read-write
    STATUS      current
    DESCRIPTION
	"The second output Max. current alarm value of slave3"
    ::= { slave3OutputCurrentMax 24}
	
slave3OutputCurrentMaxTwentyfive OBJECT-TYPE
    SYNTAX      DisplayString
    MAX-ACCESS  read-write
    STATUS      current
    DESCRIPTION
	"The second output Max. current alarm value of slave3"
    ::= { slave3OutputCurrentMax 25}
	
slave3OutputCurrentMaxTwentysix OBJECT-TYPE
    SYNTAX      DisplayString
    MAX-ACCESS  read-write
    STATUS      current
    DESCRIPTION
	"The second output Max. current alarm value of slave3"
    ::= { slave3OutputCurrentMax 26}
	
slave3OutputCurrentMaxTwentyseven OBJECT-TYPE
    SYNTAX      DisplayString
    MAX-ACCESS  read-write
    STATUS      current
    DESCRIPTION
	"The second output Max. current alarm value of slave3"
    ::= { slave3OutputCurrentMax 27}
	
slave3OutputCurrentMaxTwentyeight OBJECT-TYPE
    SYNTAX      DisplayString
    MAX-ACCESS  read-write
    STATUS      current
    DESCRIPTION
	"The second output Max. current alarm value of slave3"
    ::= { slave3OutputCurrentMax 28}	
slave3OutputCurrentMaxTwentynine OBJECT-TYPE
    SYNTAX      DisplayString
    MAX-ACCESS  read-write
    STATUS      current
    DESCRIPTION
	"The second output Max. current alarm value of slave3"
    ::= { slave3OutputCurrentMax 29}
	
slave3OutputCurrentMaxThirty OBJECT-TYPE
    SYNTAX      DisplayString
    MAX-ACCESS  read-write
    STATUS      current
    DESCRIPTION
	"The second output Max. current alarm value of slave3"
    ::= { slave3OutputCurrentMax 30}
	
slave3OutputCurrentMaxThirtyone OBJECT-TYPE
    SYNTAX      DisplayString
    MAX-ACCESS  read-write
    STATUS      current
    DESCRIPTION
	"The second output Max. current alarm value of slave3"
    ::= { slave3OutputCurrentMax 31}
	
slave3OutputCurrentMaxThirtytwo OBJECT-TYPE
    SYNTAX      DisplayString
    MAX-ACCESS  read-write
    STATUS      current
    DESCRIPTION
	"The second output Max. current alarm value of slave3"
    ::= { slave3OutputCurrentMax 32}
	
slave3OutputCurrentMaxThirtythree OBJECT-TYPE
    SYNTAX      DisplayString
    MAX-ACCESS  read-write
    STATUS      current
    DESCRIPTION
	"The second output Max. current alarm value of slave3"
    ::= { slave3OutputCurrentMax 33}
	
slave3OutputCurrentMaxThirtyfour OBJECT-TYPE
    SYNTAX      DisplayString
    MAX-ACCESS  read-write
    STATUS      current
    DESCRIPTION
	"The second output Max. current alarm value of slave3"
    ::= { slave3OutputCurrentMax 34}
	
slave3OutputCurrentMaxThirtyfive OBJECT-TYPE
    SYNTAX      DisplayString
    MAX-ACCESS  read-write
    STATUS      current
    DESCRIPTION
	"The second output Max. current alarm value of slave3"
    ::= { slave3OutputCurrentMax 35}
	
slave3OutputCurrentMaxThirtysix OBJECT-TYPE
    SYNTAX      DisplayString
    MAX-ACCESS  read-write
    STATUS      current
    DESCRIPTION
	"The second output Max. current alarm value of slave3"
    ::= { slave3OutputCurrentMax 36}
	
slave3OutputCurrentMaxThirtyseven OBJECT-TYPE
    SYNTAX      DisplayString
    MAX-ACCESS  read-write
    STATUS      current
    DESCRIPTION
	"The second output Max. current alarm value of slave3"
    ::= { slave3OutputCurrentMax 37}
	
slave3OutputCurrentMaxThirtyeight OBJECT-TYPE
    SYNTAX      DisplayString
    MAX-ACCESS  read-write
    STATUS      current
    DESCRIPTION
	"The second output Max. current alarm value of slave3"
    ::= { slave3OutputCurrentMax 38}
	
slave3OutputCurrentMaxThirtynine OBJECT-TYPE
    SYNTAX      DisplayString
    MAX-ACCESS  read-write
    STATUS      current
    DESCRIPTION
	"The second output Max. current alarm value of slave3"
    ::= { slave3OutputCurrentMax 39}
	
slave3OutputCurrentMaxFourty OBJECT-TYPE
    SYNTAX      DisplayString
    MAX-ACCESS  read-write
    STATUS      current
    DESCRIPTION
	"The second output Max. current alarm value of slave3"
    ::= { slave3OutputCurrentMax 40}
	
slave3OutputCurrentMaxFourtyone OBJECT-TYPE
    SYNTAX      DisplayString
    MAX-ACCESS  read-write
    STATUS      current
    DESCRIPTION
	"The second output Max. current alarm value of slave3"
    ::= { slave3OutputCurrentMax 41}
	
slave3OutputCurrentMaxFourtytwo OBJECT-TYPE
    SYNTAX      DisplayString
    MAX-ACCESS  read-write
    STATUS      current
    DESCRIPTION
	"The second output Max. current alarm value of slave3"
    ::= { slave3OutputCurrentMax 42}
	
	
-------------------------------slave3 output powerfactor------------------------	
slave3OutputPowerfactor OBJECT IDENTIFIER ::= { slave3 9}	

slave3OutputPowerfactorOne OBJECT-TYPE
    SYNTAX      DisplayString
    MAX-ACCESS  read-only
    STATUS      current
    DESCRIPTION
	"The ouput power factor of slave3." 
	::= { slave3OutputPowerfactor 1}

slave3OutputPowerfactorTwo OBJECT-TYPE
    SYNTAX      DisplayString
    MAX-ACCESS  read-only
    STATUS      current
    DESCRIPTION
	"The ouput power factor of slave3." 
	::= { slave3OutputPowerfactor 2}
	
slave3OutputPowerfactorThree OBJECT-TYPE
    SYNTAX      DisplayString
    MAX-ACCESS  read-only
    STATUS      current
    DESCRIPTION
	"The ouput power factor of slave3." 
	::= { slave3OutputPowerfactor 3}
	
slave3OutputPowerfactorFour OBJECT-TYPE
    SYNTAX      DisplayString
    MAX-ACCESS  read-only
    STATUS      current
    DESCRIPTION
	"The ouput power factor of slave3." 
	::= { slave3OutputPowerfactor 4}
		
slave3OutputPowerfactorFive OBJECT-TYPE
    SYNTAX      DisplayString
    MAX-ACCESS  read-only
    STATUS      current
    DESCRIPTION
	"The ouput power factor of slave3." 
	::= { slave3OutputPowerfactor 5}
	
slave3OutputPowerfactorSix OBJECT-TYPE
    SYNTAX      DisplayString
    MAX-ACCESS  read-only
    STATUS      current
    DESCRIPTION
	"The ouput power factor of slave3." 
	::= { slave3OutputPowerfactor 6}
	
slave3OutputPowerfactorSeven OBJECT-TYPE
    SYNTAX      DisplayString
    MAX-ACCESS  read-only
    STATUS      current
    DESCRIPTION
	"The ouput power factor of slave3." 
	::= { slave3OutputPowerfactor 7}	
	
slave3OutputPowerfactorEight OBJECT-TYPE
    SYNTAX      DisplayString
    MAX-ACCESS  read-only
    STATUS      current
    DESCRIPTION
	"The ouput power factor of slave3." 
	::= { slave3OutputPowerfactor 8}
	
slave3OutputPowerfactorNine OBJECT-TYPE
    SYNTAX      DisplayString
    MAX-ACCESS  read-only
    STATUS      current
    DESCRIPTION
	"The ouput power factor of slave3." 
	::= { slave3OutputPowerfactor 9}
		
slave3OutputPowerfactorTen OBJECT-TYPE
    SYNTAX      DisplayString
    MAX-ACCESS  read-only
    STATUS      current
    DESCRIPTION
	"The ouput power factor of slave3." 
	::= { slave3OutputPowerfactor 10}
		
slave3OutputPowerfactorEleven OBJECT-TYPE
    SYNTAX      DisplayString
    MAX-ACCESS  read-only
    STATUS      current
    DESCRIPTION
	"The ouput power factor of slave3." 
	::= { slave3OutputPowerfactor 11}
		
slave3OutputPowerfactorTwel OBJECT-TYPE
    SYNTAX      DisplayString
    MAX-ACCESS  read-only
    STATUS      current
    DESCRIPTION
	"The ouput power factor of slave3." 
	::= { slave3OutputPowerfactor 12}
		
slave3OutputPowerfactorThirteen OBJECT-TYPE
    SYNTAX      DisplayString
    MAX-ACCESS  read-only
    STATUS      current
    DESCRIPTION
	"The ouput power factor of slave3." 
	::= { slave3OutputPowerfactor 13}
		
slave3OutputPowerfactorFourteen OBJECT-TYPE
    SYNTAX      DisplayString
    MAX-ACCESS  read-only
    STATUS      current
    DESCRIPTION
	"The ouput power factor of slave3." 
	::= { slave3OutputPowerfactor 14}
		
slave3OutputPowerfactorFifteen OBJECT-TYPE
    SYNTAX      DisplayString
    MAX-ACCESS  read-only
    STATUS      current
    DESCRIPTION
	"The ouput power factor of slave3." 
	::= { slave3OutputPowerfactor 15}
		
slave3OutputPowerfactorSixteen OBJECT-TYPE
    SYNTAX      DisplayString
    MAX-ACCESS  read-only
    STATUS      current
    DESCRIPTION
	"The ouput power factor of slave3." 
	::= { slave3OutputPowerfactor 16}
		
slave3OutputPowerfactorSeventeen OBJECT-TYPE
    SYNTAX      DisplayString
    MAX-ACCESS  read-only
    STATUS      current
    DESCRIPTION
	"The ouput power factor of slave3." 
	::= { slave3OutputPowerfactor 17}
		
slave3OutputPowerfactorEighteen OBJECT-TYPE
    SYNTAX      DisplayString
    MAX-ACCESS  read-only
    STATUS      current
    DESCRIPTION
	"The ouput power factor of slave3." 
	::= { slave3OutputPowerfactor 18}
		
slave3OutputPowerfactorNineteen OBJECT-TYPE
    SYNTAX      DisplayString
    MAX-ACCESS  read-only
    STATUS      current
    DESCRIPTION
	"The ouput power factor of slave3." 
	::= { slave3OutputPowerfactor 19}
		
slave3OutputPowerfactorTwenty OBJECT-TYPE
    SYNTAX      DisplayString
    MAX-ACCESS  read-only
    STATUS      current
    DESCRIPTION
	"The ouput power factor of slave3." 
	::= { slave3OutputPowerfactor 20}
		
slave3OutputPowerfactorTwentyone OBJECT-TYPE
    SYNTAX      DisplayString
    MAX-ACCESS  read-only
    STATUS      current
    DESCRIPTION
	"The ouput power factor of slave3." 
	::= { slave3OutputPowerfactor 21}
		
slave3OutputPowerfactorTwentytwo OBJECT-TYPE
    SYNTAX      DisplayString
    MAX-ACCESS  read-only
    STATUS      current
    DESCRIPTION
	"The ouput power factor of slave3." 
	::= { slave3OutputPowerfactor 22}
		
slave3OutputPowerfactorTwentythree OBJECT-TYPE
    SYNTAX      DisplayString
    MAX-ACCESS  read-only
    STATUS      current
    DESCRIPTION
	"The ouput power factor of slave3." 
	::= { slave3OutputPowerfactor 23}
		
slave3OutputPowerfactorTwentyfour OBJECT-TYPE
    SYNTAX      DisplayString
    MAX-ACCESS  read-only
    STATUS      current
    DESCRIPTION
	"The ouput power factor of slave3." 
	::= { slave3OutputPowerfactor 24}
		
slave3OutputPowerfactorTwentyfive OBJECT-TYPE
    SYNTAX      DisplayString
    MAX-ACCESS  read-only
    STATUS      current
    DESCRIPTION
	"The ouput power factor of slave3." 
	::= { slave3OutputPowerfactor 25}
		
slave3OutputPowerfactorTwentysix OBJECT-TYPE
    SYNTAX      DisplayString
    MAX-ACCESS  read-only
    STATUS      current
    DESCRIPTION
	"The ouput power factor of slave3." 
	::= { slave3OutputPowerfactor 26}
		
slave3OutputPowerfactorTwentyseven OBJECT-TYPE
    SYNTAX      DisplayString
    MAX-ACCESS  read-only
    STATUS      current
    DESCRIPTION
	"The ouput power factor of slave3." 
	::= { slave3OutputPowerfactor 27}
		
slave3OutputPowerfactorTwentyeight OBJECT-TYPE
    SYNTAX      DisplayString
    MAX-ACCESS  read-only
    STATUS      current
    DESCRIPTION
	"The ouput power factor of slave3." 
	::= { slave3OutputPowerfactor 28}
		
slave3OutputPowerfactorTwentynine OBJECT-TYPE
    SYNTAX      DisplayString
    MAX-ACCESS  read-only
    STATUS      current
    DESCRIPTION
	"The ouput power factor of slave3." 
	::= { slave3OutputPowerfactor 29}
		
slave3OutputPowerfactorThirty OBJECT-TYPE
    SYNTAX      DisplayString
    MAX-ACCESS  read-only
    STATUS      current
    DESCRIPTION
	"The ouput power factor of slave3." 
	::= { slave3OutputPowerfactor 30}
		
slave3OutputPowerfactorThirtyone OBJECT-TYPE
    SYNTAX      DisplayString
    MAX-ACCESS  read-only
    STATUS      current
    DESCRIPTION
	"The ouput power factor of slave3." 
	::= { slave3OutputPowerfactor 31}
		
slave3OutputPowerfactorThirtytwo OBJECT-TYPE
    SYNTAX      DisplayString
    MAX-ACCESS  read-only
    STATUS      current
    DESCRIPTION
	"The ouput power factor of slave3." 
	::= { slave3OutputPowerfactor 32}
		
slave3OutputPowerfactorThirtythree OBJECT-TYPE
    SYNTAX      DisplayString
    MAX-ACCESS  read-only
    STATUS      current
    DESCRIPTION
	"The ouput power factor of slave3." 
	::= { slave3OutputPowerfactor 33}	
	
slave3OutputPowerfactorThirtyfour OBJECT-TYPE
    SYNTAX      DisplayString
    MAX-ACCESS  read-only
    STATUS      current
    DESCRIPTION
	"The ouput power factor of slave3." 
	::= { slave3OutputPowerfactor 34}
	
	
slave3OutputPowerfactorThirtyfive OBJECT-TYPE
    SYNTAX      DisplayString
    MAX-ACCESS  read-only
    STATUS      current
    DESCRIPTION
	"The ouput power factor of slave3." 
	::= { slave3OutputPowerfactor 35}
		
slave3OutputPowerfactorThirtysix OBJECT-TYPE
    SYNTAX      DisplayString
    MAX-ACCESS  read-only
    STATUS      current
    DESCRIPTION
	"The ouput power factor of slave3." 
	::= { slave3OutputPowerfactor 36}
		
slave3OutputPowerfactorThirtyseven OBJECT-TYPE
    SYNTAX      DisplayString
    MAX-ACCESS  read-only
    STATUS      current
    DESCRIPTION
	"The ouput power factor of slave3." 
	::= { slave3OutputPowerfactor 37}
		
slave3OutputPowerfactorThirtyeight OBJECT-TYPE
    SYNTAX      DisplayString
    MAX-ACCESS  read-only
    STATUS      current
    DESCRIPTION
	"The ouput power factor of slave3." 
	::= { slave3OutputPowerfactor 38}
		
slave3OutputPowerfactorThirtynine OBJECT-TYPE
    SYNTAX      DisplayString
    MAX-ACCESS  read-only
    STATUS      current
    DESCRIPTION
	"The ouput power factor of slave3." 
	::= { slave3OutputPowerfactor 39}
		
slave3OutputPowerfactorFourty OBJECT-TYPE
    SYNTAX      DisplayString
    MAX-ACCESS  read-only
    STATUS      current
    DESCRIPTION
	"The ouput power factor of slave3." 
	::= { slave3OutputPowerfactor 40}
		
slave3OutputPowerfactorFourtyone OBJECT-TYPE
    SYNTAX      DisplayString
    MAX-ACCESS  read-only
    STATUS      current
    DESCRIPTION
	"The ouput power factor of slave3." 
	::= { slave3OutputPowerfactor 41}
		
slave3OutputPowerfactorFourtytwo OBJECT-TYPE
    SYNTAX      DisplayString
    MAX-ACCESS  read-only
    STATUS      current
    DESCRIPTION
	"The ouput power factor of slave3." 
	::= { slave3OutputPowerfactor 42}	
	
-------------------------------slave3 output energy------------------------	
slave3OutputEnergy OBJECT IDENTIFIER ::= { slave3 10}

slave3OutputEnergyOne OBJECT-TYPE
    SYNTAX      DisplayString
    MAX-ACCESS  read-only
    STATUS      current
    DESCRIPTION
	"The ouput power of slave3." 
	::= { slave3OutputEnergy 1}

slave3OutputEnergyTwo OBJECT-TYPE
    SYNTAX      DisplayString
    MAX-ACCESS  read-only
    STATUS      current
    DESCRIPTION
	"The ouput power of slave3." 
	::= { slave3OutputEnergy 2}
	
slave3OutputEnergyThree OBJECT-TYPE
    SYNTAX      DisplayString
    MAX-ACCESS  read-only
    STATUS      current
    DESCRIPTION
	"The ouput power of slave3." 
	::= { slave3OutputEnergy 3}
	
slave3OutputEnergyFour OBJECT-TYPE
    SYNTAX      DisplayString
    MAX-ACCESS  read-only
    STATUS      current
    DESCRIPTION
	"The ouput power of slave3." 
	::= { slave3OutputEnergy 4}
		
slave3OutputEnergyFive OBJECT-TYPE
    SYNTAX      DisplayString
    MAX-ACCESS  read-only
    STATUS      current
    DESCRIPTION
	"The ouput power of slave3." 
	::= { slave3OutputEnergy 5}
	
slave3OutputEnergySix OBJECT-TYPE
    SYNTAX      DisplayString
    MAX-ACCESS  read-only
    STATUS      current
    DESCRIPTION
	"The ouput power of slave3." 
	::= { slave3OutputEnergy 6}
	
slave3OutputEnergySeven OBJECT-TYPE
    SYNTAX      DisplayString
    MAX-ACCESS  read-only
    STATUS      current
    DESCRIPTION
	"The ouput power of slave3." 
	::= { slave3OutputEnergy 7}	
	
slave3OutputEnergyEight OBJECT-TYPE
    SYNTAX      DisplayString
    MAX-ACCESS  read-only
    STATUS      current
    DESCRIPTION
	"The ouput power of slave3." 
	::= { slave3OutputEnergy 8}
	
slave3OutputEnergyNine OBJECT-TYPE
    SYNTAX      DisplayString
    MAX-ACCESS  read-only
    STATUS      current
    DESCRIPTION
	"The ouput power of slave3." 
	::= { slave3OutputEnergy 9}
		
slave3OutputEnergyTen OBJECT-TYPE
    SYNTAX      DisplayString
    MAX-ACCESS  read-only
    STATUS      current
    DESCRIPTION
	"The ouput power of slave3." 
	::= { slave3OutputEnergy 10}
		
slave3OutputEnergyEleven OBJECT-TYPE
    SYNTAX      DisplayString
    MAX-ACCESS  read-only
    STATUS      current
    DESCRIPTION
	"The ouput power of slave3." 
	::= { slave3OutputEnergy 11}
		
slave3OutputEnergyTwel OBJECT-TYPE
    SYNTAX      DisplayString
    MAX-ACCESS  read-only
    STATUS      current
    DESCRIPTION
	"The ouput power of slave3." 
	::= { slave3OutputEnergy 12}
		
slave3OutputEnergyThirteen OBJECT-TYPE
    SYNTAX      DisplayString
    MAX-ACCESS  read-only
    STATUS      current
    DESCRIPTION
	"The ouput power of slave3." 
	::= { slave3OutputEnergy 13}
		
slave3OutputEnergyFourteen OBJECT-TYPE
    SYNTAX      DisplayString
    MAX-ACCESS  read-only
    STATUS      current
    DESCRIPTION
	"The ouput power of slave3." 
	::= { slave3OutputEnergy 14}
		
slave3OutputEnergyFifteen OBJECT-TYPE
    SYNTAX      DisplayString
    MAX-ACCESS  read-only
    STATUS      current
    DESCRIPTION
	"The ouput power of slave3." 
	::= { slave3OutputEnergy 15}
		
slave3OutputEnergySixteen OBJECT-TYPE
    SYNTAX      DisplayString
    MAX-ACCESS  read-only
    STATUS      current
    DESCRIPTION
	"The ouput power of slave3." 
	::= { slave3OutputEnergy 16}
		
slave3OutputEnergySeventeen OBJECT-TYPE
    SYNTAX      DisplayString
    MAX-ACCESS  read-only
    STATUS      current
    DESCRIPTION
	"The ouput power of slave3." 
	::= { slave3OutputEnergy 17}
		
slave3OutputEnergyEighteen OBJECT-TYPE
    SYNTAX      DisplayString
    MAX-ACCESS  read-only
    STATUS      current
    DESCRIPTION
	"The ouput power of slave3." 
	::= { slave3OutputEnergy 18}
		
slave3OutputEnergyNineteen OBJECT-TYPE
    SYNTAX      DisplayString
    MAX-ACCESS  read-only
    STATUS      current
    DESCRIPTION
	"The ouput power of slave3." 
	::= { slave3OutputEnergy 19}
		
slave3OutputEnergyTwenty OBJECT-TYPE
    SYNTAX      DisplayString
    MAX-ACCESS  read-only
    STATUS      current
    DESCRIPTION
	"The ouput power of slave3." 
	::= { slave3OutputEnergy 20}
		
slave3OutputEnergyTwentyone OBJECT-TYPE
    SYNTAX      DisplayString
    MAX-ACCESS  read-only
    STATUS      current
    DESCRIPTION
	"The ouput power of slave3." 
	::= { slave3OutputEnergy 21}
		
slave3OutputEnergyTwentytwo OBJECT-TYPE
    SYNTAX      DisplayString
    MAX-ACCESS  read-only
    STATUS      current
    DESCRIPTION
	"The ouput power of slave3." 
	::= { slave3OutputEnergy 22}
		
slave3OutputEnergyTwentythree OBJECT-TYPE
    SYNTAX      DisplayString
    MAX-ACCESS  read-only
    STATUS      current
    DESCRIPTION
	"The ouput power of slave3." 
	::= { slave3OutputEnergy 23}
		
slave3OutputEnergyTwentyfour OBJECT-TYPE
    SYNTAX      DisplayString
    MAX-ACCESS  read-only
    STATUS      current
    DESCRIPTION
	"The ouput power of slave3." 
	::= { slave3OutputEnergy 24}
		
slave3OutputEnergyTwentyfive OBJECT-TYPE
    SYNTAX      DisplayString
    MAX-ACCESS  read-only
    STATUS      current
    DESCRIPTION
	"The ouput power of slave3." 
	::= { slave3OutputEnergy 25}
		
slave3OutputEnergyTwentysix OBJECT-TYPE
    SYNTAX      DisplayString
    MAX-ACCESS  read-only
    STATUS      current
    DESCRIPTION
	"The ouput power of slave3." 
	::= { slave3OutputEnergy 26}
		
slave3OutputEnergyTwentyseven OBJECT-TYPE
    SYNTAX      DisplayString
    MAX-ACCESS  read-only
    STATUS      current
    DESCRIPTION
	"The ouput power of slave3." 
	::= { slave3OutputEnergy 27}
		
slave3OutputEnergyTwentyeight OBJECT-TYPE
    SYNTAX      DisplayString
    MAX-ACCESS  read-only
    STATUS      current
    DESCRIPTION
	"The ouput power of slave3." 
	::= { slave3OutputEnergy 28}
		
slave3OutputEnergyTwentynine OBJECT-TYPE
    SYNTAX      DisplayString
    MAX-ACCESS  read-only
    STATUS      current
    DESCRIPTION
	"The ouput power of slave3." 
	::= { slave3OutputEnergy 29}
		
slave3OutputEnergyThirty OBJECT-TYPE
    SYNTAX      DisplayString
    MAX-ACCESS  read-only
    STATUS      current
    DESCRIPTION
	"The ouput power of slave3." 
	::= { slave3OutputEnergy 30}
		
slave3OutputEnergyThirtyone OBJECT-TYPE
    SYNTAX      DisplayString
    MAX-ACCESS  read-only
    STATUS      current
    DESCRIPTION
	"The ouput power of slave3." 
	::= { slave3OutputEnergy 31}
		
slave3OutputEnergyThirtytwo OBJECT-TYPE
    SYNTAX      DisplayString
    MAX-ACCESS  read-only
    STATUS      current
    DESCRIPTION
	"The ouput power of slave3." 
	::= { slave3OutputEnergy 32}
		
slave3OutputEnergyThirtythree OBJECT-TYPE
    SYNTAX      DisplayString
    MAX-ACCESS  read-only
    STATUS      current
    DESCRIPTION
	"The ouput power of slave3." 
	::= { slave3OutputEnergy 33}	
	
slave3OutputEnergyThirtyfour OBJECT-TYPE
    SYNTAX      DisplayString
    MAX-ACCESS  read-only
    STATUS      current
    DESCRIPTION
	"The ouput power of slave3." 
	::= { slave3OutputEnergy 34}
	
	
slave3OutputEnergyThirtyfive OBJECT-TYPE
    SYNTAX      DisplayString
    MAX-ACCESS  read-only
    STATUS      current
    DESCRIPTION
	"The ouput power of slave3." 
	::= { slave3OutputEnergy 35}
		
slave3OutputEnergyThirtysix OBJECT-TYPE
    SYNTAX      DisplayString
    MAX-ACCESS  read-only
    STATUS      current
    DESCRIPTION
	"The ouput power of slave3." 
	::= { slave3OutputEnergy 36}
		
slave3OutputEnergyThirtyseven OBJECT-TYPE
    SYNTAX      DisplayString
    MAX-ACCESS  read-only
    STATUS      current
    DESCRIPTION
	"The ouput power of slave3." 
	::= { slave3OutputEnergy 37}
		
slave3OutputEnergyThirtyeight OBJECT-TYPE
    SYNTAX      DisplayString
    MAX-ACCESS  read-only
    STATUS      current
    DESCRIPTION
	"The ouput power of slave3." 
	::= { slave3OutputEnergy 38}
		
slave3OutputEnergyThirtynine OBJECT-TYPE
    SYNTAX      DisplayString
    MAX-ACCESS  read-only
    STATUS      current
    DESCRIPTION
	"The ouput power of slave3." 
	::= { slave3OutputEnergy 39}
		
slave3OutputEnergyFourty OBJECT-TYPE
    SYNTAX      DisplayString
    MAX-ACCESS  read-only
    STATUS      current
    DESCRIPTION
	"The ouput power of slave3." 
	::= { slave3OutputEnergy 40}
		
slave3OutputEnergyFourtyone OBJECT-TYPE
    SYNTAX      DisplayString
    MAX-ACCESS  read-only
    STATUS      current
    DESCRIPTION
	"The ouput power of slave3." 
	::= { slave3OutputEnergy 41}
		
slave3OutputEnergyFourtytwo OBJECT-TYPE
    SYNTAX      DisplayString
    MAX-ACCESS  read-only
    STATUS      current
    DESCRIPTION
	"The ouput power of slave3." 
	::= { slave3OutputEnergy 42}	
	



-------------------------------slave4 information--------------------
slave4 OBJECT IDENTIFIER ::= { pdu 5}
slave4Information OBJECT IDENTIFIER ::= { slave4 1}
slave4Name OBJECT-TYPE
    SYNTAX      DisplayString
    MAX-ACCESS  read-write
    STATUS      current
    DESCRIPTION
	"This is the first device."
    ::= { slave4Information 1}
    
slave4Type OBJECT-TYPE
    SYNTAX      DisplayString
    MAX-ACCESS  read-only
    STATUS      current
    DESCRIPTION
	"This is device type "
    ::= { slave4Information 2}
    
slave4OutputNumber OBJECT-TYPE 
    SYNTAX      Integer32
    MAX-ACCESS  read-only
    STATUS      current
    DESCRIPTION
	"This is the number of output bits"
	::= { slave4Information 3}
	
slave4MacAdress OBJECT-TYPE
    SYNTAX      DisplayString
    MAX-ACCESS  read-only
    STATUS      current
    DESCRIPTION
	"This is device MAC adress"
    ::= { slave4Information 4}	

slave4Vison OBJECT-TYPE
    SYNTAX      DisplayString
    MAX-ACCESS  read-only
    STATUS      current
    DESCRIPTION
	"This is device vison "
    ::= { slave4Information 5}

slave4Frequency OBJECT-TYPE
    SYNTAX      Integer32
    MAX-ACCESS  read-only
    STATUS      current
    DESCRIPTION
	"This is device frequency "
    ::= { slave4Information 6}
	
slave4Emission OBJECT-TYPE
    SYNTAX      DisplayString
    MAX-ACCESS  read-only
    STATUS      current
    DESCRIPTION
	"This is device emission "
    ::= { slave4Information 7}	
	
slave4RunTime OBJECT-TYPE
    SYNTAX      DisplayString
    MAX-ACCESS  read-only
    STATUS      current
    DESCRIPTION
	"This is device running time "
    ::= { slave4Information 8}	

slave4BuzzerSwitch OBJECT-TYPE
    SYNTAX      DisplayString
    MAX-ACCESS  read-write
    STATUS      current
    DESCRIPTION
	"This is device buzzer switch."
    ::= { slave4Information 9}	

	
-------------------------------slave4 phase--------------------
slave4Phase OBJECT IDENTIFIER ::= { slave4 2}	
	
slave4PhaseOne OBJECT IDENTIFIER ::= { slave4Phase 1}	    
slave4PhaseOneCurrent OBJECT-TYPE
    SYNTAX      DisplayString
    MAX-ACCESS  read-only
    STATUS      current
    DESCRIPTION
	"The power of phase one"
    ::= { slave4PhaseOne 1}

slave4PhaseOneVoltage OBJECT-TYPE
    SYNTAX      DisplayString
    MAX-ACCESS  read-only
    STATUS      current
    DESCRIPTION
	"The power of phase one"
    ::= { slave4PhaseOne 2}

slave4PhaseOnePower OBJECT-TYPE
    SYNTAX      DisplayString
    MAX-ACCESS  read-only
    STATUS      current
    DESCRIPTION
	"The power of phase one"
    ::= { slave4PhaseOne 3}
	
slave4PhaseOnePowerfactor OBJECT-TYPE
    SYNTAX      DisplayString
    MAX-ACCESS  read-only
    STATUS      current
    DESCRIPTION
	"The power of phase one"
    ::= { slave4PhaseOne 4}	
	
slave4PhaseOneEnergy OBJECT-TYPE
    SYNTAX      DisplayString
    MAX-ACCESS  read-only
    STATUS      current
    DESCRIPTION
	"The power of phase one"
    ::= { slave4PhaseOne 5}	
		
slave4PhaseOneCurrentMin OBJECT-TYPE
    SYNTAX      DisplayString
    MAX-ACCESS  read-write
    STATUS      current
    DESCRIPTION
	"The power of phase one"
    ::= { slave4PhaseOne 6}	
	
slave4PhaseOneCurrentMinCritical OBJECT-TYPE
    SYNTAX      DisplayString
    MAX-ACCESS  read-write
    STATUS      current
    DESCRIPTION
	"The power of phase one"
    ::= { slave4PhaseOne 7}
	
slave4PhaseOneCurrentMaxCritical OBJECT-TYPE
    SYNTAX      DisplayString
    MAX-ACCESS  read-write
    STATUS      current
    DESCRIPTION
	"The power of phase one"
    ::= { slave4PhaseOne 8}
	
slave4PhaseOneCurrentMax OBJECT-TYPE
    SYNTAX      DisplayString
    MAX-ACCESS  read-write
    STATUS      current
    DESCRIPTION
	"The power of phase one"
    ::= { slave4PhaseOne 9}
	
slave4PhaseOneVoltageMin OBJECT-TYPE
    SYNTAX      DisplayString
    MAX-ACCESS  read-write
    STATUS      current
    DESCRIPTION
	"The power of phase one"
    ::= { slave4PhaseOne 10}
	
slave4PhaseOneVoltageMinCritical OBJECT-TYPE
    SYNTAX      DisplayString
    MAX-ACCESS  read-write
    STATUS      current
    DESCRIPTION
	"The power of phase one"
    ::= { slave4PhaseOne 11}

slave4PhaseOneVoltageMaxCritical OBJECT-TYPE
    SYNTAX      DisplayString
    MAX-ACCESS  read-write
    STATUS      current
    DESCRIPTION
	"The power of phase one"
    ::= { slave4PhaseOne 12}
	
slave4PhaseOneVoltageMax OBJECT-TYPE
    SYNTAX      DisplayString
    MAX-ACCESS  read-write
    STATUS      current
    DESCRIPTION
	"The power of phase one"
    ::= { slave4PhaseOne 13}


slave4PhaseTwo OBJECT IDENTIFIER ::= { slave4Phase 2}	    
slave4PhaseTwoCurrent OBJECT-TYPE
    SYNTAX      DisplayString
    MAX-ACCESS  read-only
    STATUS      current
    DESCRIPTION
	"The power of phase one"
    ::= { slave4PhaseTwo 1}

slave4PhaseTwoVoltage OBJECT-TYPE
    SYNTAX      DisplayString
    MAX-ACCESS  read-only
    STATUS      current
    DESCRIPTION
	"The power of phase one"
    ::= { slave4PhaseTwo 2}

slave4PhaseTwoPower OBJECT-TYPE
    SYNTAX      DisplayString
    MAX-ACCESS  read-only
    STATUS      current
    DESCRIPTION
	"The power of phase one"
    ::= { slave4PhaseTwo 3}
	
slave4PhaseTwoPowerfactor OBJECT-TYPE
    SYNTAX      DisplayString
    MAX-ACCESS  read-only
    STATUS      current
    DESCRIPTION
	"The power of phase one"
    ::= { slave4PhaseTwo 4}	
	
slave4PhaseTwoEnergy OBJECT-TYPE
    SYNTAX      DisplayString
    MAX-ACCESS  read-only
    STATUS      current
    DESCRIPTION
	"The power of phase one"
    ::= { slave4PhaseTwo 5}	
		
slave4PhaseTwoCurrentMin OBJECT-TYPE
    SYNTAX      DisplayString
    MAX-ACCESS  read-write
    STATUS      current
    DESCRIPTION
	"The power of phase one"
    ::= { slave4PhaseTwo 6}	
	
slave4PhaseTwoCurrentMinCritical OBJECT-TYPE
    SYNTAX      DisplayString
    MAX-ACCESS  read-write
    STATUS      current
    DESCRIPTION
	"The power of phase one"
    ::= { slave4PhaseTwo 7}
	
slave4PhaseTwoCurrentMaxCritical OBJECT-TYPE
    SYNTAX      DisplayString
    MAX-ACCESS  read-write
    STATUS      current
    DESCRIPTION
	"The power of phase one"
    ::= { slave4PhaseTwo 8}
	
slave4PhaseTwoCurrentMax OBJECT-TYPE
    SYNTAX      DisplayString
    MAX-ACCESS  read-write
    STATUS      current
    DESCRIPTION
	"The power of phase one"
    ::= { slave4PhaseTwo 9}
	
slave4PhaseTwoVoltageMin OBJECT-TYPE
    SYNTAX      DisplayString
    MAX-ACCESS  read-write
    STATUS      current
    DESCRIPTION
	"The power of phase one"
    ::= { slave4PhaseTwo 10}
	
slave4PhaseTwoVoltageMinCritical OBJECT-TYPE
    SYNTAX      DisplayString
    MAX-ACCESS  read-write
    STATUS      current
    DESCRIPTION
	"The power of phase one"
    ::= { slave4PhaseTwo 11}

slave4PhaseTwoVoltageMaxCritical OBJECT-TYPE
    SYNTAX      DisplayString
    MAX-ACCESS  read-write
    STATUS      current
    DESCRIPTION
	"The power of phase one"
    ::= { slave4PhaseTwo 12}
	
slave4PhaseTwoVoltageMax OBJECT-TYPE
    SYNTAX      DisplayString
    MAX-ACCESS  read-write
    STATUS      current
    DESCRIPTION
	"The power of phase one"
    ::= { slave4PhaseTwo 13}
	
	
slave4PhaseThree OBJECT IDENTIFIER ::= { slave4Phase 3}	    
slave4PhaseThreeCurrent OBJECT-TYPE
    SYNTAX      DisplayString
    MAX-ACCESS  read-only
    STATUS      current
    DESCRIPTION
	"The power of phase one"
    ::= { slave4PhaseThree 1}

slave4PhaseThreeVoltage OBJECT-TYPE
    SYNTAX      DisplayString
    MAX-ACCESS  read-only
    STATUS      current
    DESCRIPTION
	"The power of phase one"
    ::= { slave4PhaseThree 2}

slave4PhaseThreePower OBJECT-TYPE
    SYNTAX      DisplayString
    MAX-ACCESS  read-only
    STATUS      current
    DESCRIPTION
	"The power of phase one"
    ::= { slave4PhaseThree 3}
	
slave4PhaseThreePowerfactor OBJECT-TYPE
    SYNTAX      DisplayString
    MAX-ACCESS  read-only
    STATUS      current
    DESCRIPTION
	"The power of phase one"
    ::= { slave4PhaseThree 4}	
	
slave4PhaseThreeEnergy OBJECT-TYPE
    SYNTAX      DisplayString
    MAX-ACCESS  read-only
    STATUS      current
    DESCRIPTION
	"The power of phase one"
    ::= { slave4PhaseThree 5}	
		
slave4PhaseThreeCurrentMin OBJECT-TYPE
    SYNTAX      DisplayString
    MAX-ACCESS  read-write
    STATUS      current
    DESCRIPTION
	"The power of phase one"
    ::= { slave4PhaseThree 6}	
	
slave4PhaseThreeCurrentMinCritical OBJECT-TYPE
    SYNTAX      DisplayString
    MAX-ACCESS  read-write
    STATUS      current
    DESCRIPTION
	"The power of phase one"
    ::= { slave4PhaseThree 7}
	
slave4PhaseThreeCurrentMaxCritical OBJECT-TYPE
    SYNTAX      DisplayString
    MAX-ACCESS  read-write
    STATUS      current
    DESCRIPTION
	"The power of phase one"
    ::= { slave4PhaseThree 8}
	
slave4PhaseThreeCurrentMax OBJECT-TYPE
    SYNTAX      DisplayString
    MAX-ACCESS  read-write
    STATUS      current
    DESCRIPTION
	"The power of phase one"
    ::= { slave4PhaseThree 9}
	
slave4PhaseThreeVoltageMin OBJECT-TYPE
    SYNTAX      DisplayString
    MAX-ACCESS  read-write
    STATUS      current
    DESCRIPTION
	"The power of phase one"
    ::= { slave4PhaseThree 10}
	
slave4PhaseThreeVoltageMinCritical OBJECT-TYPE
    SYNTAX      DisplayString
    MAX-ACCESS  read-write
    STATUS      current
    DESCRIPTION
	"The power of phase one"
    ::= { slave4PhaseThree 11}

slave4PhaseThreeVoltageMaxCritical OBJECT-TYPE
    SYNTAX      DisplayString
    MAX-ACCESS  read-write
    STATUS      current
    DESCRIPTION
	"The power of phase one"
    ::= { slave4PhaseThree 12}
	
slave4PhaseThreeVoltageMax OBJECT-TYPE
    SYNTAX      DisplayString
    MAX-ACCESS  read-write
    STATUS      current
    DESCRIPTION
	"The power of phase one"
    ::= { slave4PhaseThree 13}
	
	
-------------------------------slave4 circuit--------------------	
slave4Circuit OBJECT IDENTIFIER ::= { slave4 3}	

slave4CircuitOne OBJECT IDENTIFIER ::= { slave4Circuit 1}	    
slave4CircuitOneBreaker OBJECT-TYPE
    SYNTAX      DisplayString
    MAX-ACCESS  read-only
    STATUS      current
    DESCRIPTION
	"The power of phase one"
    ::= { slave4CircuitOne 1}
	
slave4CircuitOneManagementBit OBJECT-TYPE
    SYNTAX      DisplayString
    MAX-ACCESS  read-only
    STATUS      current
    DESCRIPTION
	"The power of phase one"
    ::= { slave4CircuitOne 2}	

slave4CircuitOneCurrent OBJECT-TYPE
    SYNTAX      DisplayString
    MAX-ACCESS  read-only
    STATUS      current
    DESCRIPTION
	"The power of phase one"
    ::= { slave4CircuitOne 3}

slave4CircuitOneVoltage OBJECT-TYPE
    SYNTAX      DisplayString
    MAX-ACCESS  read-only
    STATUS      current
    DESCRIPTION
	"The power of phase one"
    ::= { slave4CircuitOne 4}

slave4CircuitOneEnergy OBJECT-TYPE
    SYNTAX      DisplayString
    MAX-ACCESS  read-only
    STATUS      current
    DESCRIPTION
	"The power of phase one"
    ::= { slave4CircuitOne 5}	
	
slave4CircuitOnePower OBJECT-TYPE
    SYNTAX      DisplayString
    MAX-ACCESS  read-only
    STATUS      current
    DESCRIPTION
	"The power of phase one"
    ::= { slave4CircuitOne 6}
	
slave4CircuitOneCurrentMin OBJECT-TYPE
    SYNTAX      DisplayString
    MAX-ACCESS  read-write
    STATUS      current
    DESCRIPTION
	"The power of phase one"
    ::= { slave4CircuitOne 7}	
	
slave4CircuitOneCurrentMinCritical OBJECT-TYPE
    SYNTAX      DisplayString
    MAX-ACCESS  read-write
    STATUS      current
    DESCRIPTION
	"The power of phase one"
    ::= { slave4CircuitOne 8}
	
slave4CircuitOneCurrentMaxCritical OBJECT-TYPE
    SYNTAX      DisplayString
    MAX-ACCESS  read-write
    STATUS      current
    DESCRIPTION
	"The power of phase one"
    ::= { slave4CircuitOne 9}
	
slave4CircuitOneCurrentMax OBJECT-TYPE
    SYNTAX      DisplayString
    MAX-ACCESS  read-write
    STATUS      current
    DESCRIPTION
	"The power of phase one"
    ::= { slave4CircuitOne 10}
	

slave4CircuitTwo OBJECT IDENTIFIER ::= { slave4Circuit 2}	    
slave4CircuitTwoBreaker OBJECT-TYPE
    SYNTAX      DisplayString
    MAX-ACCESS  read-only
    STATUS      current
    DESCRIPTION
	"The power of phase one"
    ::= { slave4CircuitTwo 1}
	
slave4CircuitTwoManagementBit OBJECT-TYPE
    SYNTAX      DisplayString
    MAX-ACCESS  read-only
    STATUS      current
    DESCRIPTION
	"The power of phase one"
    ::= { slave4CircuitTwo 2}	

slave4CircuitTwoCurrent OBJECT-TYPE
    SYNTAX      DisplayString
    MAX-ACCESS  read-only
    STATUS      current
    DESCRIPTION
	"The power of phase one"
    ::= { slave4CircuitTwo 3}

slave4CircuitTwoVoltage OBJECT-TYPE
    SYNTAX      DisplayString
    MAX-ACCESS  read-only
    STATUS      current
    DESCRIPTION
	"The power of phase one"
    ::= { slave4CircuitTwo 4}

slave4CircuitTwoEnergy OBJECT-TYPE
    SYNTAX      DisplayString
    MAX-ACCESS  read-only
    STATUS      current
    DESCRIPTION
	"The power of phase one"
    ::= { slave4CircuitTwo 5}	
	
slave4CircuitTwoPower OBJECT-TYPE
    SYNTAX      DisplayString
    MAX-ACCESS  read-only
    STATUS      current
    DESCRIPTION
	"The power of phase one"
    ::= { slave4CircuitTwo 6}
	
slave4CircuitTwoCurrentMin OBJECT-TYPE
    SYNTAX      DisplayString
    MAX-ACCESS  read-write
    STATUS      current
    DESCRIPTION
	"The power of phase one"
    ::= { slave4CircuitTwo 7}	
	
slave4CircuitTwoCurrentMinCritical OBJECT-TYPE
    SYNTAX      DisplayString
    MAX-ACCESS  read-write
    STATUS      current
    DESCRIPTION
	"The power of phase one"
    ::= { slave4CircuitTwo 8}
	
slave4CircuitTwoCurrentMaxCritical OBJECT-TYPE
    SYNTAX      DisplayString
    MAX-ACCESS  read-write
    STATUS      current
    DESCRIPTION
	"The power of phase one"
    ::= { slave4CircuitTwo 9}
	
slave4CircuitTwoCurrentMax OBJECT-TYPE
    SYNTAX      DisplayString
    MAX-ACCESS  read-write
    STATUS      current
    DESCRIPTION
	"The power of phase one"
    ::= { slave4CircuitTwo 10}
	
	
slave4CircuitThree OBJECT IDENTIFIER ::= { slave4Circuit 3}	    
slave4CircuitThreeBreaker OBJECT-TYPE
    SYNTAX      DisplayString
    MAX-ACCESS  read-only
    STATUS      current
    DESCRIPTION
	"The power of phase one"
    ::= { slave4CircuitThree 1}
	
slave4CircuitThreeManagementBit OBJECT-TYPE
    SYNTAX      DisplayString
    MAX-ACCESS  read-only
    STATUS      current
    DESCRIPTION
	"The power of phase one"
    ::= { slave4CircuitThree 2}	

slave4CircuitThreeCurrent OBJECT-TYPE
    SYNTAX      DisplayString
    MAX-ACCESS  read-only
    STATUS      current
    DESCRIPTION
	"The power of phase one"
    ::= { slave4CircuitThree 3}

slave4CircuitThreeVoltage OBJECT-TYPE
    SYNTAX      DisplayString
    MAX-ACCESS  read-only
    STATUS      current
    DESCRIPTION
	"The power of phase one"
    ::= { slave4CircuitThree 4}

slave4CircuitThreeEnergy OBJECT-TYPE
    SYNTAX      DisplayString
    MAX-ACCESS  read-only
    STATUS      current
    DESCRIPTION
	"The power of phase one"
    ::= { slave4CircuitThree 5}	
	
slave4CircuitThreePower OBJECT-TYPE
    SYNTAX      DisplayString
    MAX-ACCESS  read-only
    STATUS      current
    DESCRIPTION
	"The power of phase one"
    ::= { slave4CircuitThree 6}
	
slave4CircuitThreeCurrentMin OBJECT-TYPE
    SYNTAX      DisplayString
    MAX-ACCESS  read-write
    STATUS      current
    DESCRIPTION
	"The power of phase one"
    ::= { slave4CircuitThree 7}	
	
slave4CircuitThreeCurrentMinCritical OBJECT-TYPE
    SYNTAX      DisplayString
    MAX-ACCESS  read-write
    STATUS      current
    DESCRIPTION
	"The power of phase one"
    ::= { slave4CircuitThree 8}
	
slave4CircuitThreeCurrentMaxCritical OBJECT-TYPE
    SYNTAX      DisplayString
    MAX-ACCESS  read-write
    STATUS      current
    DESCRIPTION
	"The power of phase one"
    ::= { slave4CircuitThree 9}
	
slave4CircuitThreeCurrentMax OBJECT-TYPE
    SYNTAX      DisplayString
    MAX-ACCESS  read-write
    STATUS      current
    DESCRIPTION
	"The power of phase one"
    ::= { slave4CircuitThree 10}
	
	
slave4CircuitFour OBJECT IDENTIFIER ::= { slave4Circuit 4}	    
slave4CircuitFourBreaker OBJECT-TYPE
    SYNTAX      DisplayString
    MAX-ACCESS  read-only
    STATUS      current
    DESCRIPTION
	"The power of phase one"
    ::= { slave4CircuitFour 1}
	
slave4CircuitFourManagementBit OBJECT-TYPE
    SYNTAX      DisplayString
    MAX-ACCESS  read-only
    STATUS      current
    DESCRIPTION
	"The power of phase one"
    ::= { slave4CircuitFour 2}	

slave4CircuitFourCurrent OBJECT-TYPE
    SYNTAX      DisplayString
    MAX-ACCESS  read-only
    STATUS      current
    DESCRIPTION
	"The power of phase one"
    ::= { slave4CircuitFour 3}

slave4CircuitFourVoltage OBJECT-TYPE
    SYNTAX      DisplayString
    MAX-ACCESS  read-only
    STATUS      current
    DESCRIPTION
	"The power of phase one"
    ::= { slave4CircuitFour 4}

slave4CircuitFourEnergy OBJECT-TYPE
    SYNTAX      DisplayString
    MAX-ACCESS  read-only
    STATUS      current
    DESCRIPTION
	"The power of phase one"
    ::= { slave4CircuitFour 5}	
	
slave4CircuitFourPower OBJECT-TYPE
    SYNTAX      DisplayString
    MAX-ACCESS  read-only
    STATUS      current
    DESCRIPTION
	"The power of phase one"
    ::= { slave4CircuitFour 6}
	
slave4CircuitFourCurrentMin OBJECT-TYPE
    SYNTAX      DisplayString
    MAX-ACCESS  read-write
    STATUS      current
    DESCRIPTION
	"The power of phase one"
    ::= { slave4CircuitFour 7}	
	
slave4CircuitFourCurrentMinCritical OBJECT-TYPE
    SYNTAX      DisplayString
    MAX-ACCESS  read-write
    STATUS      current
    DESCRIPTION
	"The power of phase one"
    ::= { slave4CircuitFour 8}
	
slave4CircuitFourCurrentMaxCritical OBJECT-TYPE
    SYNTAX      DisplayString
    MAX-ACCESS  read-write
    STATUS      current
    DESCRIPTION
	"The power of phase one"
    ::= { slave4CircuitFour 9}
	
slave4CircuitFourCurrentMax OBJECT-TYPE
    SYNTAX      DisplayString
    MAX-ACCESS  read-write
    STATUS      current
    DESCRIPTION
	"The power of phase one"
    ::= { slave4CircuitFour 10}
	
	
slave4CircuitFive OBJECT IDENTIFIER ::= { slave4Circuit 5}	    
slave4CircuitFiveBreaker OBJECT-TYPE
    SYNTAX      DisplayString
    MAX-ACCESS  read-only
    STATUS      current
    DESCRIPTION
	"The power of phase one"
    ::= { slave4CircuitFive 1}
	
slave4CircuitFiveManagementBit OBJECT-TYPE
    SYNTAX      DisplayString
    MAX-ACCESS  read-only
    STATUS      current
    DESCRIPTION
	"The power of phase one"
    ::= { slave4CircuitFive 2}	

slave4CircuitFiveCurrent OBJECT-TYPE
    SYNTAX      DisplayString
    MAX-ACCESS  read-only
    STATUS      current
    DESCRIPTION
	"The power of phase one"
    ::= { slave4CircuitFive 3}

slave4CircuitFiveVoltage OBJECT-TYPE
    SYNTAX      DisplayString
    MAX-ACCESS  read-only
    STATUS      current
    DESCRIPTION
	"The power of phase one"
    ::= { slave4CircuitFive 4}

slave4CircuitFiveEnergy OBJECT-TYPE
    SYNTAX      DisplayString
    MAX-ACCESS  read-only
    STATUS      current
    DESCRIPTION
	"The power of phase one"
    ::= { slave4CircuitFive 5}	
	
slave4CircuitFivePower OBJECT-TYPE
    SYNTAX      DisplayString
    MAX-ACCESS  read-only
    STATUS      current
    DESCRIPTION
	"The power of phase one"
    ::= { slave4CircuitFive 6}
		
slave4CircuitFiveCurrentMin OBJECT-TYPE
    SYNTAX      DisplayString
    MAX-ACCESS  read-write
    STATUS      current
    DESCRIPTION
	"The power of phase one"
    ::= { slave4CircuitFive 7}	
	
slave4CircuitFiveCurrentMinCritical OBJECT-TYPE
    SYNTAX      DisplayString
    MAX-ACCESS  read-write
    STATUS      current
    DESCRIPTION
	"The power of phase one"
    ::= { slave4CircuitFive 8}
	
slave4CircuitFiveCurrentMaxCritical OBJECT-TYPE
    SYNTAX      DisplayString
    MAX-ACCESS  read-write
    STATUS      current
    DESCRIPTION
	"The power of phase one"
    ::= { slave4CircuitFive 9}
	
slave4CircuitFiveCurrentMax OBJECT-TYPE
    SYNTAX      DisplayString
    MAX-ACCESS  read-write
    STATUS      current
    DESCRIPTION
	"The power of phase one"
    ::= { slave4CircuitFive 10}

	
slave4CircuitSix OBJECT IDENTIFIER ::= { slave4Circuit 6}	    
slave4CircuitSixBreaker OBJECT-TYPE
    SYNTAX      DisplayString
    MAX-ACCESS  read-only
    STATUS      current
    DESCRIPTION
	"The power of phase one"
    ::= { slave4CircuitSix 1}
	
slave4CircuitSixManagementBit OBJECT-TYPE
    SYNTAX      DisplayString
    MAX-ACCESS  read-only
    STATUS      current
    DESCRIPTION
	"The power of phase one"
    ::= { slave4CircuitSix 2}	

slave4CircuitSixCurrent OBJECT-TYPE
    SYNTAX      DisplayString
    MAX-ACCESS  read-only
    STATUS      current
    DESCRIPTION
	"The power of phase one"
    ::= { slave4CircuitSix 3}

slave4CircuitSixVoltage OBJECT-TYPE
    SYNTAX      DisplayString
    MAX-ACCESS  read-only
    STATUS      current
    DESCRIPTION
	"The power of phase one"
    ::= { slave4CircuitSix 4}

slave4CircuitSixEnergy OBJECT-TYPE
    SYNTAX      DisplayString
    MAX-ACCESS  read-only
    STATUS      current
    DESCRIPTION
	"The power of phase one"
    ::= { slave4CircuitSix 5}	
	
slave4CircuitSixPower OBJECT-TYPE
    SYNTAX      DisplayString
    MAX-ACCESS  read-only
    STATUS      current
    DESCRIPTION
	"The power of phase one"
    ::= { slave4CircuitSix 6}
	
slave4CircuitSixCurrentMin OBJECT-TYPE
    SYNTAX      DisplayString
    MAX-ACCESS  read-write
    STATUS      current
    DESCRIPTION
	"The power of phase one"
    ::= { slave4CircuitSix 7}	
	
slave4CircuitSixCurrentMinCritical OBJECT-TYPE
    SYNTAX      DisplayString
    MAX-ACCESS  read-write
    STATUS      current
    DESCRIPTION
	"The power of phase one"
    ::= { slave4CircuitSix 8}
	
slave4CircuitSixCurrentMaxCritical OBJECT-TYPE
    SYNTAX      DisplayString
    MAX-ACCESS  read-write
    STATUS      current
    DESCRIPTION
	"The power of phase one"
    ::= { slave4CircuitSix 9}
	
slave4CircuitSixCurrentMax OBJECT-TYPE
    SYNTAX      DisplayString
    MAX-ACCESS  read-write
    STATUS      current
    DESCRIPTION
	"The power of phase one"
    ::= { slave4CircuitSix 10}

	
-------------------------------slave4 sensor------------------------	
slave4Sensor OBJECT IDENTIFIER ::= { slave4 4}
slave4SensorTemperatureOne OBJECT-TYPE
    SYNTAX      DisplayString
    MAX-ACCESS  read-only
    STATUS      current
    DESCRIPTION
	"This is the first device."
    ::= { slave4Sensor 1}
	
slave4SensorTemperatureTwo OBJECT-TYPE
    SYNTAX      DisplayString
    MAX-ACCESS  read-only
    STATUS      current
    DESCRIPTION
	"This is the first device."
    ::= { slave4Sensor 2}

slave4SensorHumidityOne OBJECT-TYPE
    SYNTAX      DisplayString
    MAX-ACCESS  read-only
    STATUS      current
    DESCRIPTION
	"This is the first device."
    ::= { slave4Sensor 3}

slave4SensorHumidityTwo OBJECT-TYPE
    SYNTAX      DisplayString
    MAX-ACCESS  read-only
    STATUS      current
    DESCRIPTION
	"This is the first device."
    ::= { slave4Sensor 4}	

slave4SensorDoorOne OBJECT-TYPE
    SYNTAX      DisplayString
    MAX-ACCESS  read-only
    STATUS      current
    DESCRIPTION
	"This is the first device."
    ::= { slave4Sensor 5}

slave4SensorDoorTwo OBJECT-TYPE
    SYNTAX      DisplayString
    MAX-ACCESS  read-only
    STATUS      current
    DESCRIPTION
	"This is the first device."
    ::= { slave4Sensor 6}	
	
slave4SensorSmoke OBJECT-TYPE
    SYNTAX      DisplayString
    MAX-ACCESS  read-only
    STATUS      current
    DESCRIPTION
	"This is the first device."
    ::= { slave4Sensor 7}
	
slave4SensorWater OBJECT-TYPE
    SYNTAX      DisplayString
    MAX-ACCESS  read-only
    STATUS      current
    DESCRIPTION
	"This is the first device."
    ::= { slave4Sensor 8}
	
slave4SensorTemperatureOneMin OBJECT-TYPE
    SYNTAX      DisplayString
    MAX-ACCESS  read-write
    STATUS      current
    DESCRIPTION
	"This is the first device."
    ::= { slave4Sensor 9}
	
slave4SensorTemperatureOneMinCritical OBJECT-TYPE
    SYNTAX      DisplayString
    MAX-ACCESS  read-write
    STATUS      current
    DESCRIPTION
	"This is the first device."
    ::= { slave4Sensor 10}	
	
slave4SensorTemperatureOneMaxCritical OBJECT-TYPE
    SYNTAX      DisplayString
    MAX-ACCESS  read-write
    STATUS      current
    DESCRIPTION
	"This is the first device."
    ::= { slave4Sensor 11}
	
slave4SensorTemperatureOneMax OBJECT-TYPE
    SYNTAX      DisplayString
    MAX-ACCESS  read-write
    STATUS      current
    DESCRIPTION
	"This is the first device."
    ::= { slave4Sensor 12}

slave4SensorTemperatureTwoMin OBJECT-TYPE
    SYNTAX      DisplayString
    MAX-ACCESS  read-write
    STATUS      current
    DESCRIPTION
	"This is the first device."
    ::= { slave4Sensor 13}
	
slave4SensorTemperatureTwoMinCritical OBJECT-TYPE
    SYNTAX      DisplayString
    MAX-ACCESS  read-write
    STATUS      current
    DESCRIPTION
	"This is the first device."
    ::= { slave4Sensor 14}	
	
slave4SensorTemperatureTwoMaxCritical OBJECT-TYPE
    SYNTAX      DisplayString
    MAX-ACCESS  read-write
    STATUS      current
    DESCRIPTION
	"This is the first device."
    ::= { slave4Sensor 15}
	
slave4SensorTemperatureTwoMax OBJECT-TYPE
    SYNTAX      DisplayString
    MAX-ACCESS  read-write
    STATUS      current
    DESCRIPTION
	"This is the first device."
    ::= { slave4Sensor 16}
	
slave4SensorHumidityOneMin OBJECT-TYPE
    SYNTAX      DisplayString
    MAX-ACCESS  read-write
    STATUS      current
    DESCRIPTION
	"This is the first device."
    ::= { slave4Sensor 17}
	
slave4SensorHumidityOneMinCritical OBJECT-TYPE
    SYNTAX      DisplayString
    MAX-ACCESS  read-write
    STATUS      current
    DESCRIPTION
	"This is the first device."
    ::= { slave4Sensor 18}	
	
slave4SensorHumidityOneMaxCritical OBJECT-TYPE
    SYNTAX      DisplayString
    MAX-ACCESS  read-write
    STATUS      current
    DESCRIPTION
	"This is the first device."
    ::= { slave4Sensor 19}
	
slave4SensorHumidityOneMax OBJECT-TYPE
    SYNTAX      DisplayString
    MAX-ACCESS  read-write
    STATUS      current
    DESCRIPTION
	"This is the first device."
    ::= { slave4Sensor 20}

slave4SensorHumidityTwoMin OBJECT-TYPE
    SYNTAX      DisplayString
    MAX-ACCESS  read-write
    STATUS      current
    DESCRIPTION
	"This is the first device."
    ::= { slave4Sensor 21}
	
slave4SensorHumidityTwoMinCritical OBJECT-TYPE
    SYNTAX      DisplayString
    MAX-ACCESS  read-write
    STATUS      current
    DESCRIPTION
	"This is the first device."
    ::= { slave4Sensor 22}	
	
slave4SensorHumidityTwoMaxCritical OBJECT-TYPE
    SYNTAX      DisplayString
    MAX-ACCESS  read-write
    STATUS      current
    DESCRIPTION
	"This is the first device."
    ::= { slave4Sensor 23}
	
slave4SensorHumidityTwoMax OBJECT-TYPE
    SYNTAX      DisplayString
    MAX-ACCESS  read-write
    STATUS      current
    DESCRIPTION
	"This is the first device."
    ::= { slave4Sensor 24}
	
-------------------------------slave4 output name------------------------	
slave4OutputName OBJECT IDENTIFIER ::= { slave4 5}
slave4OutputNameOne OBJECT-TYPE
    SYNTAX      DisplayString
    MAX-ACCESS  read-write
    STATUS      current
    DESCRIPTION
	"The first output name of slave4"
    ::= { slave4OutputName 1}

slave4OutputNameTwo OBJECT-TYPE
    SYNTAX      DisplayString
    MAX-ACCESS  read-write
    STATUS      current
    DESCRIPTION
	"The second output name of slave4"
    ::= { slave4OutputName 2}

slave4OutputNameThree OBJECT-TYPE
    SYNTAX      DisplayString
    MAX-ACCESS  read-write
    STATUS      current
    DESCRIPTION
	"The second output name of slave4"
    ::= { slave4OutputName 3}

slave4OutputNameFour OBJECT-TYPE
    SYNTAX      DisplayString
    MAX-ACCESS  read-write
    STATUS      current
    DESCRIPTION
	"The second output name of slave4"
    ::= { slave4OutputName 4}

slave4OutputNameFive OBJECT-TYPE
    SYNTAX      DisplayString
    MAX-ACCESS  read-write
    STATUS      current
    DESCRIPTION
	"The second output name of slave4"
    ::= { slave4OutputName 5}

slave4OutputNameSix OBJECT-TYPE
    SYNTAX      DisplayString
    MAX-ACCESS  read-write
    STATUS      current
    DESCRIPTION
	"The second output name of slave4"
    ::= { slave4OutputName 6}

slave4OutputNameSeven OBJECT-TYPE
    SYNTAX      DisplayString
    MAX-ACCESS  read-write
    STATUS      current
    DESCRIPTION
	"The second output name of slave4"
    ::= { slave4OutputName 7}

slave4OutputNameEight OBJECT-TYPE
    SYNTAX      DisplayString
    MAX-ACCESS  read-write
    STATUS      current
    DESCRIPTION
	"The second output name of slave4"
    ::= { slave4OutputName 8}

slave4OutputNameNine OBJECT-TYPE
    SYNTAX      DisplayString
    MAX-ACCESS  read-write
    STATUS      current
    DESCRIPTION
	"The second output name of slave4"
    ::= { slave4OutputName 9}

slave4OutputNameTen OBJECT-TYPE
    SYNTAX      DisplayString
    MAX-ACCESS  read-write
    STATUS      current
    DESCRIPTION
	"The second output name of slave4"
    ::= { slave4OutputName 10}

slave4OutputNameEleven OBJECT-TYPE
    SYNTAX      DisplayString
    MAX-ACCESS  read-write
    STATUS      current
    DESCRIPTION
	"The second output name of slave4"
    ::= { slave4OutputName 11}

slave4OutputNameTwel OBJECT-TYPE
    SYNTAX      DisplayString
    MAX-ACCESS  read-write
    STATUS      current
    DESCRIPTION
	"The second output name of slave4"
    ::= { slave4OutputName 12}

slave4OutputNameThirteen OBJECT-TYPE
    SYNTAX      DisplayString
    MAX-ACCESS  read-write
    STATUS      current
    DESCRIPTION
	"The second output name of slave4"
    ::= { slave4OutputName 13}

slave4OutputNameFourteen OBJECT-TYPE
    SYNTAX      DisplayString
    MAX-ACCESS  read-write
    STATUS      current
    DESCRIPTION
	"The second output name of slave4"
    ::= { slave4OutputName 14}

slave4OutputNameFifteen OBJECT-TYPE
    SYNTAX      DisplayString
    MAX-ACCESS  read-write
    STATUS      current
    DESCRIPTION
	"The second output name of slave4"
    ::= { slave4OutputName 15}

slave4OutputNameSixteen OBJECT-TYPE
    SYNTAX      DisplayString
    MAX-ACCESS  read-write
    STATUS      current
    DESCRIPTION
	"The second output name of slave4"
    ::= { slave4OutputName 16}

slave4OutputNameSeventeen OBJECT-TYPE
    SYNTAX      DisplayString
    MAX-ACCESS  read-write
    STATUS      current
    DESCRIPTION
	"The second output name of slave4"
    ::= { slave4OutputName 17}

slave4OutputNameEighteen OBJECT-TYPE
    SYNTAX      DisplayString
    MAX-ACCESS  read-write
    STATUS      current
    DESCRIPTION
	"The second output name of slave4"
    ::= { slave4OutputName 18}
	
slave4OutputNameNineteen OBJECT-TYPE
    SYNTAX      DisplayString
    MAX-ACCESS  read-write
    STATUS      current
    DESCRIPTION
	"The second output name of slave4"
    ::= { slave4OutputName 19}
	
slave4OutputNametwenty OBJECT-TYPE
    SYNTAX      DisplayString
    MAX-ACCESS  read-write
    STATUS      current
    DESCRIPTION
	"The second output name of slave4"
    ::= { slave4OutputName 20}
	
slave4OutputNameTwentyone OBJECT-TYPE
    SYNTAX      DisplayString
    MAX-ACCESS  read-write
    STATUS      current
    DESCRIPTION
	"The second output name of slave4"
    ::= { slave4OutputName 21}
	
slave4OutputNameTwentyonetwo OBJECT-TYPE
    SYNTAX      DisplayString
    MAX-ACCESS  read-write
    STATUS      current
    DESCRIPTION
	"The second output name of slave4"
    ::= { slave4OutputName 22}
	
slave4OutputNameTwentythree OBJECT-TYPE
    SYNTAX      DisplayString
    MAX-ACCESS  read-write
    STATUS      current
    DESCRIPTION
	"The second output name of slave4"
    ::= { slave4OutputName 23}
	
slave4OutputNameTwentyfour OBJECT-TYPE
    SYNTAX      DisplayString
    MAX-ACCESS  read-write
    STATUS      current
    DESCRIPTION
	"The second output name of slave4"
    ::= { slave4OutputName 24}
	
slave4OutputNameTwentyfive OBJECT-TYPE
    SYNTAX      DisplayString
    MAX-ACCESS  read-write
    STATUS      current
    DESCRIPTION
	"The second output name of slave4"
    ::= { slave4OutputName 25}
	
slave4OutputNameTwentysix OBJECT-TYPE
    SYNTAX      DisplayString
    MAX-ACCESS  read-write
    STATUS      current
    DESCRIPTION
	"The second output name of slave4"
    ::= { slave4OutputName 26}
	
slave4OutputNameTwentyseven OBJECT-TYPE
    SYNTAX      DisplayString
    MAX-ACCESS  read-write
    STATUS      current
    DESCRIPTION
	"The second output name of slave4"
    ::= { slave4OutputName 27}
	
slave4OutputNameTwentyeight OBJECT-TYPE
    SYNTAX      DisplayString
    MAX-ACCESS  read-write
    STATUS      current
    DESCRIPTION
	"The second output name of slave4"
    ::= { slave4OutputName 28}	
slave4OutputNameTwentynine OBJECT-TYPE
    SYNTAX      DisplayString
    MAX-ACCESS  read-write
    STATUS      current
    DESCRIPTION
	"The second output name of slave4"
    ::= { slave4OutputName 29}
	
slave4OutputNameThirty OBJECT-TYPE
    SYNTAX      DisplayString
    MAX-ACCESS  read-write
    STATUS      current
    DESCRIPTION
	"The second output name of slave4"
    ::= { slave4OutputName 30}
	
slave4OutputNameThirtyone OBJECT-TYPE
    SYNTAX      DisplayString
    MAX-ACCESS  read-write
    STATUS      current
    DESCRIPTION
	"The second output name of slave4"
    ::= { slave4OutputName 31}
	
slave4OutputNameThirtytwo OBJECT-TYPE
    SYNTAX      DisplayString
    MAX-ACCESS  read-write
    STATUS      current
    DESCRIPTION
	"The second output name of slave4"
    ::= { slave4OutputName 32}
	
slave4OutputNameThirtythree OBJECT-TYPE
    SYNTAX      DisplayString
    MAX-ACCESS  read-write
    STATUS      current
    DESCRIPTION
	"The second output name of slave4"
    ::= { slave4OutputName 33}
	
slave4OutputNameThirtyfour OBJECT-TYPE
    SYNTAX      DisplayString
    MAX-ACCESS  read-write
    STATUS      current
    DESCRIPTION
	"The second output name of slave4"
    ::= { slave4OutputName 34}
	
slave4OutputNameThirtyfive OBJECT-TYPE
    SYNTAX      DisplayString
    MAX-ACCESS  read-write
    STATUS      current
    DESCRIPTION
	"The second output name of slave4"
    ::= { slave4OutputName 35}
	
slave4OutputNameThirtysix OBJECT-TYPE
    SYNTAX      DisplayString
    MAX-ACCESS  read-write
    STATUS      current
    DESCRIPTION
	"The second output name of slave4"
    ::= { slave4OutputName 36}
	
slave4OutputNameThirtyseven OBJECT-TYPE
    SYNTAX      DisplayString
    MAX-ACCESS  read-write
    STATUS      current
    DESCRIPTION
	"The second output name of slave4"
    ::= { slave4OutputName 37}
	
slave4OutputNameThirtyeight OBJECT-TYPE
    SYNTAX      DisplayString
    MAX-ACCESS  read-write
    STATUS      current
    DESCRIPTION
	"The second output name of slave4"
    ::= { slave4OutputName 38}
	
slave4OutputNameThirtynine OBJECT-TYPE
    SYNTAX      DisplayString
    MAX-ACCESS  read-write
    STATUS      current
    DESCRIPTION
	"The second output name of slave4"
    ::= { slave4OutputName 39}
	
slave4OutputNameFourty OBJECT-TYPE
    SYNTAX      DisplayString
    MAX-ACCESS  read-write
    STATUS      current
    DESCRIPTION
	"The second output name of slave4"
    ::= { slave4OutputName 40}
	
slave4OutputNameFourtyone OBJECT-TYPE
    SYNTAX      DisplayString
    MAX-ACCESS  read-write
    STATUS      current
    DESCRIPTION
	"The second output name of slave4"
    ::= { slave4OutputName 41}
	
slave4OutputNameFourtytwo OBJECT-TYPE
    SYNTAX      DisplayString
    MAX-ACCESS  read-write
    STATUS      current
    DESCRIPTION
	"The second output name of slave4"
    ::= { slave4OutputName 42}	

	
-------------------------------slave4 output delay------------------------	
slave4OutputDelay OBJECT IDENTIFIER ::= { slave4 6}	
slave4OutputDelayOne OBJECT-TYPE
    SYNTAX      DisplayString
    MAX-ACCESS  read-write
    STATUS      current
    DESCRIPTION
	"The first output name of slave4"
    ::= { slave4OutputDelay 1}

slave4OutputDelayTwo OBJECT-TYPE
    SYNTAX      DisplayString
    MAX-ACCESS  read-write
    STATUS      current
    DESCRIPTION
	"The second output name of slave4"
    ::= { slave4OutputDelay 2}

slave4OutputDelayThree OBJECT-TYPE
    SYNTAX      DisplayString
    MAX-ACCESS  read-write
    STATUS      current
    DESCRIPTION
	"The second output name of slave4"
    ::= { slave4OutputDelay 3}

slave4OutputDelayFour OBJECT-TYPE
    SYNTAX      DisplayString
    MAX-ACCESS  read-write
    STATUS      current
    DESCRIPTION
	"The second output name of slave4"
    ::= { slave4OutputDelay 4}

slave4OutputDelayFive OBJECT-TYPE
    SYNTAX      DisplayString
    MAX-ACCESS  read-write
    STATUS      current
    DESCRIPTION
	"The second output name of slave4"
    ::= { slave4OutputDelay 5}

slave4OutputDelaySix OBJECT-TYPE
    SYNTAX      DisplayString
    MAX-ACCESS  read-write
    STATUS      current
    DESCRIPTION
	"The second output name of slave4"
    ::= { slave4OutputDelay 6}

slave4OutputDelaySeven OBJECT-TYPE
    SYNTAX      DisplayString
    MAX-ACCESS  read-write
    STATUS      current
    DESCRIPTION
	"The second output name of slave4"
    ::= { slave4OutputDelay 7}

slave4OutputDelayEight OBJECT-TYPE
    SYNTAX      DisplayString
    MAX-ACCESS  read-write
    STATUS      current
    DESCRIPTION
	"The second output name of slave4"
    ::= { slave4OutputDelay 8}

slave4OutputDelayNine OBJECT-TYPE
    SYNTAX      DisplayString
    MAX-ACCESS  read-write
    STATUS      current
    DESCRIPTION
	"The second output name of slave4"
    ::= { slave4OutputDelay 9}

slave4OutputDelayTen OBJECT-TYPE
    SYNTAX      DisplayString
    MAX-ACCESS  read-write
    STATUS      current
    DESCRIPTION
	"The second output name of slave4"
    ::= { slave4OutputDelay 10}

slave4OutputDelayEleven OBJECT-TYPE
    SYNTAX      DisplayString
    MAX-ACCESS  read-write
    STATUS      current
    DESCRIPTION
	"The second output name of slave4"
    ::= { slave4OutputDelay 11}

slave4OutputDelayTwel OBJECT-TYPE
    SYNTAX      DisplayString
    MAX-ACCESS  read-write
    STATUS      current
    DESCRIPTION
	"The second output name of slave4"
    ::= { slave4OutputDelay 12}

slave4OutputDelayThirteen OBJECT-TYPE
    SYNTAX      DisplayString
    MAX-ACCESS  read-write
    STATUS      current
    DESCRIPTION
	"The second output name of slave4"
    ::= { slave4OutputDelay 13}

slave4OutputDelayFourteen OBJECT-TYPE
    SYNTAX      DisplayString
    MAX-ACCESS  read-write
    STATUS      current
    DESCRIPTION
	"The second output name of slave4"
    ::= { slave4OutputDelay 14}

slave4OutputDelayFifteen OBJECT-TYPE
    SYNTAX      DisplayString
    MAX-ACCESS  read-write
    STATUS      current
    DESCRIPTION
	"The second output name of slave4"
    ::= { slave4OutputDelay 15}

slave4OutputDelaySixteen OBJECT-TYPE
    SYNTAX      DisplayString
    MAX-ACCESS  read-write
    STATUS      current
    DESCRIPTION
	"The second output name of slave4"
    ::= { slave4OutputDelay 16}

slave4OutputDelaySeventeen OBJECT-TYPE
    SYNTAX      DisplayString
    MAX-ACCESS  read-write
    STATUS      current
    DESCRIPTION
	"The second output name of slave4"
    ::= { slave4OutputDelay 17}

slave4OutputDelayEighteen OBJECT-TYPE
    SYNTAX      DisplayString
    MAX-ACCESS  read-write
    STATUS      current
    DESCRIPTION
	"The second output name of slave4"
    ::= { slave4OutputDelay 18}
	
slave4OutputDelayNineteen OBJECT-TYPE
    SYNTAX      DisplayString
    MAX-ACCESS  read-write
    STATUS      current
    DESCRIPTION
	"The second output name of slave4"
    ::= { slave4OutputDelay 19}
	
slave4OutputDelaytwenty OBJECT-TYPE
    SYNTAX      DisplayString
    MAX-ACCESS  read-write
    STATUS      current
    DESCRIPTION
	"The second output name of slave4"
    ::= { slave4OutputDelay 20}
	
slave4OutputDelayTwentyone OBJECT-TYPE
    SYNTAX      DisplayString
    MAX-ACCESS  read-write
    STATUS      current
    DESCRIPTION
	"The second output name of slave4"
    ::= { slave4OutputDelay 21}
	
slave4OutputDelayTwentyonetwo OBJECT-TYPE
    SYNTAX      DisplayString
    MAX-ACCESS  read-write
    STATUS      current
    DESCRIPTION
	"The second output name of slave4"
    ::= { slave4OutputDelay 22}
	
slave4OutputDelayTwentythree OBJECT-TYPE
    SYNTAX      DisplayString
    MAX-ACCESS  read-write
    STATUS      current
    DESCRIPTION
	"The second output name of slave4"
    ::= { slave4OutputDelay 23}
	
slave4OutputDelayTwentyfour OBJECT-TYPE
    SYNTAX      DisplayString
    MAX-ACCESS  read-write
    STATUS      current
    DESCRIPTION
	"The second output name of slave4"
    ::= { slave4OutputDelay 24}
	
slave4OutputDelayTwentyfive OBJECT-TYPE
    SYNTAX      DisplayString
    MAX-ACCESS  read-write
    STATUS      current
    DESCRIPTION
	"The second output name of slave4"
    ::= { slave4OutputDelay 25}
	
slave4OutputDelayTwentysix OBJECT-TYPE
    SYNTAX      DisplayString
    MAX-ACCESS  read-write
    STATUS      current
    DESCRIPTION
	"The second output name of slave4"
    ::= { slave4OutputDelay 26}
	
slave4OutputDelayTwentyseven OBJECT-TYPE
    SYNTAX      DisplayString
    MAX-ACCESS  read-write
    STATUS      current
    DESCRIPTION
	"The second output name of slave4"
    ::= { slave4OutputDelay 27}
	
slave4OutputDelayTwentyeight OBJECT-TYPE
    SYNTAX      DisplayString
    MAX-ACCESS  read-write
    STATUS      current
    DESCRIPTION
	"The second output name of slave4"
    ::= { slave4OutputDelay 28}	
slave4OutputDelayTwentynine OBJECT-TYPE
    SYNTAX      DisplayString
    MAX-ACCESS  read-write
    STATUS      current
    DESCRIPTION
	"The second output name of slave4"
    ::= { slave4OutputDelay 29}
	
slave4OutputDelayThirty OBJECT-TYPE
    SYNTAX      DisplayString
    MAX-ACCESS  read-write
    STATUS      current
    DESCRIPTION
	"The second output name of slave4"
    ::= { slave4OutputDelay 30}
	
slave4OutputDelayThirtyone OBJECT-TYPE
    SYNTAX      DisplayString
    MAX-ACCESS  read-write
    STATUS      current
    DESCRIPTION
	"The second output name of slave4"
    ::= { slave4OutputDelay 31}
	
slave4OutputDelayThirtytwo OBJECT-TYPE
    SYNTAX      DisplayString
    MAX-ACCESS  read-write
    STATUS      current
    DESCRIPTION
	"The second output name of slave4"
    ::= { slave4OutputDelay 32}
	
slave4OutputDelayThirtythree OBJECT-TYPE
    SYNTAX      DisplayString
    MAX-ACCESS  read-write
    STATUS      current
    DESCRIPTION
	"The second output name of slave4"
    ::= { slave4OutputDelay 33}
	
slave4OutputDelayThirtyfour OBJECT-TYPE
    SYNTAX      DisplayString
    MAX-ACCESS  read-write
    STATUS      current
    DESCRIPTION
	"The second output name of slave4"
    ::= { slave4OutputDelay 34}
	
slave4OutputDelayThirtyfive OBJECT-TYPE
    SYNTAX      DisplayString
    MAX-ACCESS  read-write
    STATUS      current
    DESCRIPTION
	"The second output name of slave4"
    ::= { slave4OutputDelay 35}
	
slave4OutputDelayThirtysix OBJECT-TYPE
    SYNTAX      DisplayString
    MAX-ACCESS  read-write
    STATUS      current
    DESCRIPTION
	"The second output name of slave4"
    ::= { slave4OutputDelay 36}
	
slave4OutputDelayThirtyseven OBJECT-TYPE
    SYNTAX      DisplayString
    MAX-ACCESS  read-write
    STATUS      current
    DESCRIPTION
	"The second output name of slave4"
    ::= { slave4OutputDelay 37}
	
slave4OutputDelayThirtyeight OBJECT-TYPE
    SYNTAX      DisplayString
    MAX-ACCESS  read-write
    STATUS      current
    DESCRIPTION
	"The second output name of slave4"
    ::= { slave4OutputDelay 38}
	
slave4OutputDelayThirtynine OBJECT-TYPE
    SYNTAX      DisplayString
    MAX-ACCESS  read-write
    STATUS      current
    DESCRIPTION
	"The second output name of slave4"
    ::= { slave4OutputDelay 39}
	
slave4OutputDelayFourty OBJECT-TYPE
    SYNTAX      DisplayString
    MAX-ACCESS  read-write
    STATUS      current
    DESCRIPTION
	"The second output name of slave4"
    ::= { slave4OutputDelay 40}
	
slave4OutputDelayFourtyone OBJECT-TYPE
    SYNTAX      DisplayString
    MAX-ACCESS  read-write
    STATUS      current
    DESCRIPTION
	"The second output name of slave4"
    ::= { slave4OutputDelay 41}
	
slave4OutputDelayFourtytwo OBJECT-TYPE
    SYNTAX      DisplayString
    MAX-ACCESS  read-write
    STATUS      current
    DESCRIPTION
	"The second output name of slave4"
    ::= { slave4OutputDelay 42}

	
-------------------------------slave4 output switch------------------------	
slave4OutputSwitch OBJECT IDENTIFIER ::= { slave4 7}		
slave4OutputSwitchOne OBJECT-TYPE
    SYNTAX      DisplayString
    MAX-ACCESS  read-write
    STATUS      current
    DESCRIPTION
	"The first output name of slave4"
    ::= { slave4OutputSwitch 1}

slave4OutputSwitchTwo OBJECT-TYPE
    SYNTAX      DisplayString
    MAX-ACCESS  read-write
    STATUS      current
    DESCRIPTION
	"The second output name of slave4"
    ::= { slave4OutputSwitch 2}

slave4OutputSwitchThree OBJECT-TYPE
    SYNTAX      DisplayString
    MAX-ACCESS  read-write
    STATUS      current
    DESCRIPTION
	"The second output name of slave4"
    ::= { slave4OutputSwitch 3}

slave4OutputSwitchFour OBJECT-TYPE
    SYNTAX      DisplayString
    MAX-ACCESS  read-write
    STATUS      current
    DESCRIPTION
	"The second output name of slave4"
    ::= { slave4OutputSwitch 4}

slave4OutputSwitchFive OBJECT-TYPE
    SYNTAX      DisplayString
    MAX-ACCESS  read-write
    STATUS      current
    DESCRIPTION
	"The second output name of slave4"
    ::= { slave4OutputSwitch 5}

slave4OutputSwitchSix OBJECT-TYPE
    SYNTAX      DisplayString
    MAX-ACCESS  read-write
    STATUS      current
    DESCRIPTION
	"The second output name of slave4"
    ::= { slave4OutputSwitch 6}

slave4OutputSwitchSeven OBJECT-TYPE
    SYNTAX      DisplayString
    MAX-ACCESS  read-write
    STATUS      current
    DESCRIPTION
	"The second output name of slave4"
    ::= { slave4OutputSwitch 7}

slave4OutputSwitchEight OBJECT-TYPE
    SYNTAX      DisplayString
    MAX-ACCESS  read-write
    STATUS      current
    DESCRIPTION
	"The second output name of slave4"
    ::= { slave4OutputSwitch 8}

slave4OutputSwitchNine OBJECT-TYPE
    SYNTAX      DisplayString
    MAX-ACCESS  read-write
    STATUS      current
    DESCRIPTION
	"The second output name of slave4"
    ::= { slave4OutputSwitch 9}

slave4OutputSwitchTen OBJECT-TYPE
    SYNTAX      DisplayString
    MAX-ACCESS  read-write
    STATUS      current
    DESCRIPTION
	"The second output name of slave4"
    ::= { slave4OutputSwitch 10}

slave4OutputSwitchEleven OBJECT-TYPE
    SYNTAX      DisplayString
    MAX-ACCESS  read-write
    STATUS      current
    DESCRIPTION
	"The second output name of slave4"
    ::= { slave4OutputSwitch 11}

slave4OutputSwitchTwel OBJECT-TYPE
    SYNTAX      DisplayString
    MAX-ACCESS  read-write
    STATUS      current
    DESCRIPTION
	"The second output name of slave4"
    ::= { slave4OutputSwitch 12}

slave4OutputSwitchThirteen OBJECT-TYPE
    SYNTAX      DisplayString
    MAX-ACCESS  read-write
    STATUS      current
    DESCRIPTION
	"The second output name of slave4"
    ::= { slave4OutputSwitch 13}

slave4OutputSwitchFourteen OBJECT-TYPE
    SYNTAX      DisplayString
    MAX-ACCESS  read-write
    STATUS      current
    DESCRIPTION
	"The second output name of slave4"
    ::= { slave4OutputSwitch 14}

slave4OutputSwitchFifteen OBJECT-TYPE
    SYNTAX      DisplayString
    MAX-ACCESS  read-write
    STATUS      current
    DESCRIPTION
	"The second output name of slave4"
    ::= { slave4OutputSwitch 15}

slave4OutputSwitchSixteen OBJECT-TYPE
    SYNTAX      DisplayString
    MAX-ACCESS  read-write
    STATUS      current
    DESCRIPTION
	"The second output name of slave4"
    ::= { slave4OutputSwitch 16}

slave4OutputSwitchSeventeen OBJECT-TYPE
    SYNTAX      DisplayString
    MAX-ACCESS  read-write
    STATUS      current
    DESCRIPTION
	"The second output name of slave4"
    ::= { slave4OutputSwitch 17}

slave4OutputSwitchEighteen OBJECT-TYPE
    SYNTAX      DisplayString
    MAX-ACCESS  read-write
    STATUS      current
    DESCRIPTION
	"The second output name of slave4"
    ::= { slave4OutputSwitch 18}
	
slave4OutputSwitchNineteen OBJECT-TYPE
    SYNTAX      DisplayString
    MAX-ACCESS  read-write
    STATUS      current
    DESCRIPTION
	"The second output name of slave4"
    ::= { slave4OutputSwitch 19}
	
slave4OutputSwitchtwenty OBJECT-TYPE
    SYNTAX      DisplayString
    MAX-ACCESS  read-write
    STATUS      current
    DESCRIPTION
	"The second output name of slave4"
    ::= { slave4OutputSwitch 20}
	
slave4OutputSwitchTwentyone OBJECT-TYPE
    SYNTAX      DisplayString
    MAX-ACCESS  read-write
    STATUS      current
    DESCRIPTION
	"The second output name of slave4"
    ::= { slave4OutputSwitch 21}
	
slave4OutputSwitchTwentyonetwo OBJECT-TYPE
    SYNTAX      DisplayString
    MAX-ACCESS  read-write
    STATUS      current
    DESCRIPTION
	"The second output name of slave4"
    ::= { slave4OutputSwitch 22}
	
slave4OutputSwitchTwentythree OBJECT-TYPE
    SYNTAX      DisplayString
    MAX-ACCESS  read-write
    STATUS      current
    DESCRIPTION
	"The second output name of slave4"
    ::= { slave4OutputSwitch 23}
	
slave4OutputSwitchTwentyfour OBJECT-TYPE
    SYNTAX      DisplayString
    MAX-ACCESS  read-write
    STATUS      current
    DESCRIPTION
	"The second output name of slave4"
    ::= { slave4OutputSwitch 24}
	
slave4OutputSwitchTwentyfive OBJECT-TYPE
    SYNTAX      DisplayString
    MAX-ACCESS  read-write
    STATUS      current
    DESCRIPTION
	"The second output name of slave4"
    ::= { slave4OutputSwitch 25}
	
slave4OutputSwitchTwentysix OBJECT-TYPE
    SYNTAX      DisplayString
    MAX-ACCESS  read-write
    STATUS      current
    DESCRIPTION
	"The second output name of slave4"
    ::= { slave4OutputSwitch 26}
	
slave4OutputSwitchTwentyseven OBJECT-TYPE
    SYNTAX      DisplayString
    MAX-ACCESS  read-write
    STATUS      current
    DESCRIPTION
	"The second output name of slave4"
    ::= { slave4OutputSwitch 27}
	
slave4OutputSwitchTwentyeight OBJECT-TYPE
    SYNTAX      DisplayString
    MAX-ACCESS  read-write
    STATUS      current
    DESCRIPTION
	"The second output name of slave4"
    ::= { slave4OutputSwitch 28}	
slave4OutputSwitchTwentynine OBJECT-TYPE
    SYNTAX      DisplayString
    MAX-ACCESS  read-write
    STATUS      current
    DESCRIPTION
	"The second output name of slave4"
    ::= { slave4OutputSwitch 29}
	
slave4OutputSwitchThirty OBJECT-TYPE
    SYNTAX      DisplayString
    MAX-ACCESS  read-write
    STATUS      current
    DESCRIPTION
	"The second output name of slave4"
    ::= { slave4OutputSwitch 30}
	
slave4OutputSwitchThirtyone OBJECT-TYPE
    SYNTAX      DisplayString
    MAX-ACCESS  read-write
    STATUS      current
    DESCRIPTION
	"The second output name of slave4"
    ::= { slave4OutputSwitch 31}
	
slave4OutputSwitchThirtytwo OBJECT-TYPE
    SYNTAX      DisplayString
    MAX-ACCESS  read-write
    STATUS      current
    DESCRIPTION
	"The second output name of slave4"
    ::= { slave4OutputSwitch 32}
	
slave4OutputSwitchThirtythree OBJECT-TYPE
    SYNTAX      DisplayString
    MAX-ACCESS  read-write
    STATUS      current
    DESCRIPTION
	"The second output name of slave4"
    ::= { slave4OutputSwitch 33}
	
slave4OutputSwitchThirtyfour OBJECT-TYPE
    SYNTAX      DisplayString
    MAX-ACCESS  read-write
    STATUS      current
    DESCRIPTION
	"The second output name of slave4"
    ::= { slave4OutputSwitch 34}
	
slave4OutputSwitchThirtyfive OBJECT-TYPE
    SYNTAX      DisplayString
    MAX-ACCESS  read-write
    STATUS      current
    DESCRIPTION
	"The second output name of slave4"
    ::= { slave4OutputSwitch 35}
	
slave4OutputSwitchThirtysix OBJECT-TYPE
    SYNTAX      DisplayString
    MAX-ACCESS  read-write
    STATUS      current
    DESCRIPTION
	"The second output name of slave4"
    ::= { slave4OutputSwitch 36}
	
slave4OutputSwitchThirtyseven OBJECT-TYPE
    SYNTAX      DisplayString
    MAX-ACCESS  read-write
    STATUS      current
    DESCRIPTION
	"The second output name of slave4"
    ::= { slave4OutputSwitch 37}
	
slave4OutputSwitchThirtyeight OBJECT-TYPE
    SYNTAX      DisplayString
    MAX-ACCESS  read-write
    STATUS      current
    DESCRIPTION
	"The second output name of slave4"
    ::= { slave4OutputSwitch 38}
	
slave4OutputSwitchThirtynine OBJECT-TYPE
    SYNTAX      DisplayString
    MAX-ACCESS  read-write
    STATUS      current
    DESCRIPTION
	"The second output name of slave4"
    ::= { slave4OutputSwitch 39}
	
slave4OutputSwitchFourty OBJECT-TYPE
    SYNTAX      DisplayString
    MAX-ACCESS  read-write
    STATUS      current
    DESCRIPTION
	"The second output name of slave4"
    ::= { slave4OutputSwitch 40}
	
slave4OutputSwitchFourtyone OBJECT-TYPE
    SYNTAX      DisplayString
    MAX-ACCESS  read-write
    STATUS      current
    DESCRIPTION
	"The second output name of slave4"
    ::= { slave4OutputSwitch 41}
	
slave4OutputSwitchFourtytwo OBJECT-TYPE
    SYNTAX      DisplayString
    MAX-ACCESS  read-write
    STATUS      current
    DESCRIPTION
	"The second output name of slave4"
    ::= { slave4OutputSwitch 42}

	
-------------------------------slave4 output current------------------------	
slave4OutputCurrent OBJECT IDENTIFIER ::= { slave4 8}		
slave4OutputCurrentValue OBJECT IDENTIFIER ::= { slave4OutputCurrent 1}	

slave4OutputCurrentValueOne OBJECT-TYPE
    SYNTAX      DisplayString
    MAX-ACCESS  read-write
    STATUS      current
    DESCRIPTION
	"The first output name of slave4"
    ::= { slave4OutputCurrentValue 1}

slave4OutputCurrentValueTwo OBJECT-TYPE
    SYNTAX      DisplayString
    MAX-ACCESS  read-write
    STATUS      current
    DESCRIPTION
	"The second output name of slave4"
    ::= { slave4OutputCurrentValue 2}

slave4OutputCurrentValueThree OBJECT-TYPE
    SYNTAX      DisplayString
    MAX-ACCESS  read-write
    STATUS      current
    DESCRIPTION
	"The second output name of slave4"
    ::= { slave4OutputCurrentValue 3}

slave4OutputCurrentValueFour OBJECT-TYPE
    SYNTAX      DisplayString
    MAX-ACCESS  read-write
    STATUS      current
    DESCRIPTION
	"The second output name of slave4"
    ::= { slave4OutputCurrentValue 4}

slave4OutputCurrentValueFive OBJECT-TYPE
    SYNTAX      DisplayString
    MAX-ACCESS  read-write
    STATUS      current
    DESCRIPTION
	"The second output name of slave4"
    ::= { slave4OutputCurrentValue 5}

slave4OutputCurrentValueSix OBJECT-TYPE
    SYNTAX      DisplayString
    MAX-ACCESS  read-write
    STATUS      current
    DESCRIPTION
	"The second output name of slave4"
    ::= { slave4OutputCurrentValue 6}

slave4OutputCurrentValueSeven OBJECT-TYPE
    SYNTAX      DisplayString
    MAX-ACCESS  read-write
    STATUS      current
    DESCRIPTION
	"The second output name of slave4"
    ::= { slave4OutputCurrentValue 7}

slave4OutputCurrentValueEight OBJECT-TYPE
    SYNTAX      DisplayString
    MAX-ACCESS  read-write
    STATUS      current
    DESCRIPTION
	"The second output name of slave4"
    ::= { slave4OutputCurrentValue 8}

slave4OutputCurrentValueNine OBJECT-TYPE
    SYNTAX      DisplayString
    MAX-ACCESS  read-write
    STATUS      current
    DESCRIPTION
	"The second output name of slave4"
    ::= { slave4OutputCurrentValue 9}

slave4OutputCurrentValueTen OBJECT-TYPE
    SYNTAX      DisplayString
    MAX-ACCESS  read-write
    STATUS      current
    DESCRIPTION
	"The second output name of slave4"
    ::= { slave4OutputCurrentValue 10}

slave4OutputCurrentValueEleven OBJECT-TYPE
    SYNTAX      DisplayString
    MAX-ACCESS  read-write
    STATUS      current
    DESCRIPTION
	"The second output name of slave4"
    ::= { slave4OutputCurrentValue 11}

slave4OutputCurrentValueTwel OBJECT-TYPE
    SYNTAX      DisplayString
    MAX-ACCESS  read-write
    STATUS      current
    DESCRIPTION
	"The second output name of slave4"
    ::= { slave4OutputCurrentValue 12}

slave4OutputCurrentValueThirteen OBJECT-TYPE
    SYNTAX      DisplayString
    MAX-ACCESS  read-write
    STATUS      current
    DESCRIPTION
	"The second output name of slave4"
    ::= { slave4OutputCurrentValue 13}

slave4OutputCurrentValueFourteen OBJECT-TYPE
    SYNTAX      DisplayString
    MAX-ACCESS  read-write
    STATUS      current
    DESCRIPTION
	"The second output name of slave4"
    ::= { slave4OutputCurrentValue 14}

slave4OutputCurrentValueFifteen OBJECT-TYPE
    SYNTAX      DisplayString
    MAX-ACCESS  read-write
    STATUS      current
    DESCRIPTION
	"The second output name of slave4"
    ::= { slave4OutputCurrentValue 15}

slave4OutputCurrentValueSixteen OBJECT-TYPE
    SYNTAX      DisplayString
    MAX-ACCESS  read-write
    STATUS      current
    DESCRIPTION
	"The second output name of slave4"
    ::= { slave4OutputCurrentValue 16}

slave4OutputCurrentValueSeventeen OBJECT-TYPE
    SYNTAX      DisplayString
    MAX-ACCESS  read-write
    STATUS      current
    DESCRIPTION
	"The second output name of slave4"
    ::= { slave4OutputCurrentValue 17}

slave4OutputCurrentValueEighteen OBJECT-TYPE
    SYNTAX      DisplayString
    MAX-ACCESS  read-write
    STATUS      current
    DESCRIPTION
	"The second output name of slave4"
    ::= { slave4OutputCurrentValue 18}
	
slave4OutputCurrentValueNineteen OBJECT-TYPE
    SYNTAX      DisplayString
    MAX-ACCESS  read-write
    STATUS      current
    DESCRIPTION
	"The second output name of slave4"
    ::= { slave4OutputCurrentValue 19}
	
slave4OutputCurrentValuetwenty OBJECT-TYPE
    SYNTAX      DisplayString
    MAX-ACCESS  read-write
    STATUS      current
    DESCRIPTION
	"The second output name of slave4"
    ::= { slave4OutputCurrentValue 20}
	
slave4OutputCurrentValueTwentyone OBJECT-TYPE
    SYNTAX      DisplayString
    MAX-ACCESS  read-write
    STATUS      current
    DESCRIPTION
	"The second output name of slave4"
    ::= { slave4OutputCurrentValue 21}
	
slave4OutputCurrentValueTwentyonetwo OBJECT-TYPE
    SYNTAX      DisplayString
    MAX-ACCESS  read-write
    STATUS      current
    DESCRIPTION
	"The second output name of slave4"
    ::= { slave4OutputCurrentValue 22}
	
slave4OutputCurrentValueTwentythree OBJECT-TYPE
    SYNTAX      DisplayString
    MAX-ACCESS  read-write
    STATUS      current
    DESCRIPTION
	"The second output name of slave4"
    ::= { slave4OutputCurrentValue 23}
	
slave4OutputCurrentValueTwentyfour OBJECT-TYPE
    SYNTAX      DisplayString
    MAX-ACCESS  read-write
    STATUS      current
    DESCRIPTION
	"The second output name of slave4"
    ::= { slave4OutputCurrentValue 24}
	
slave4OutputCurrentValueTwentyfive OBJECT-TYPE
    SYNTAX      DisplayString
    MAX-ACCESS  read-write
    STATUS      current
    DESCRIPTION
	"The second output name of slave4"
    ::= { slave4OutputCurrentValue 25}
	
slave4OutputCurrentValueTwentysix OBJECT-TYPE
    SYNTAX      DisplayString
    MAX-ACCESS  read-write
    STATUS      current
    DESCRIPTION
	"The second output name of slave4"
    ::= { slave4OutputCurrentValue 26}
	
slave4OutputCurrentValueTwentyseven OBJECT-TYPE
    SYNTAX      DisplayString
    MAX-ACCESS  read-write
    STATUS      current
    DESCRIPTION
	"The second output name of slave4"
    ::= { slave4OutputCurrentValue 27}
	
slave4OutputCurrentValueTwentyeight OBJECT-TYPE
    SYNTAX      DisplayString
    MAX-ACCESS  read-write
    STATUS      current
    DESCRIPTION
	"The second output name of slave4"
    ::= { slave4OutputCurrentValue 28}	
slave4OutputCurrentValueTwentynine OBJECT-TYPE
    SYNTAX      DisplayString
    MAX-ACCESS  read-write
    STATUS      current
    DESCRIPTION
	"The second output name of slave4"
    ::= { slave4OutputCurrentValue 29}
	
slave4OutputCurrentValueThirty OBJECT-TYPE
    SYNTAX      DisplayString
    MAX-ACCESS  read-write
    STATUS      current
    DESCRIPTION
	"The second output name of slave4"
    ::= { slave4OutputCurrentValue 30}
	
slave4OutputCurrentValueThirtyone OBJECT-TYPE
    SYNTAX      DisplayString
    MAX-ACCESS  read-write
    STATUS      current
    DESCRIPTION
	"The second output name of slave4"
    ::= { slave4OutputCurrentValue 31}
	
slave4OutputCurrentValueThirtytwo OBJECT-TYPE
    SYNTAX      DisplayString
    MAX-ACCESS  read-write
    STATUS      current
    DESCRIPTION
	"The second output name of slave4"
    ::= { slave4OutputCurrentValue 32}
	
slave4OutputCurrentValueThirtythree OBJECT-TYPE
    SYNTAX      DisplayString
    MAX-ACCESS  read-write
    STATUS      current
    DESCRIPTION
	"The second output name of slave4"
    ::= { slave4OutputCurrentValue 33}
	
slave4OutputCurrentValueThirtyfour OBJECT-TYPE
    SYNTAX      DisplayString
    MAX-ACCESS  read-write
    STATUS      current
    DESCRIPTION
	"The second output name of slave4"
    ::= { slave4OutputCurrentValue 34}
	
slave4OutputCurrentValueThirtyfive OBJECT-TYPE
    SYNTAX      DisplayString
    MAX-ACCESS  read-write
    STATUS      current
    DESCRIPTION
	"The second output name of slave4"
    ::= { slave4OutputCurrentValue 35}
	
slave4OutputCurrentValueThirtysix OBJECT-TYPE
    SYNTAX      DisplayString
    MAX-ACCESS  read-write
    STATUS      current
    DESCRIPTION
	"The second output name of slave4"
    ::= { slave4OutputCurrentValue 36}
	
slave4OutputCurrentValueThirtyseven OBJECT-TYPE
    SYNTAX      DisplayString
    MAX-ACCESS  read-write
    STATUS      current
    DESCRIPTION
	"The second output name of slave4"
    ::= { slave4OutputCurrentValue 37}
	
slave4OutputCurrentValueThirtyeight OBJECT-TYPE
    SYNTAX      DisplayString
    MAX-ACCESS  read-write
    STATUS      current
    DESCRIPTION
	"The second output name of slave4"
    ::= { slave4OutputCurrentValue 38}
	
slave4OutputCurrentValueThirtynine OBJECT-TYPE
    SYNTAX      DisplayString
    MAX-ACCESS  read-write
    STATUS      current
    DESCRIPTION
	"The second output name of slave4"
    ::= { slave4OutputCurrentValue 39}
	
slave4OutputCurrentValueFourty OBJECT-TYPE
    SYNTAX      DisplayString
    MAX-ACCESS  read-write
    STATUS      current
    DESCRIPTION
	"The second output name of slave4"
    ::= { slave4OutputCurrentValue 40}
	
slave4OutputCurrentValueFourtyone OBJECT-TYPE
    SYNTAX      DisplayString
    MAX-ACCESS  read-write
    STATUS      current
    DESCRIPTION
	"The second output name of slave4"
    ::= { slave4OutputCurrentValue 41}
	
slave4OutputCurrentValueFourtytwo OBJECT-TYPE
    SYNTAX      DisplayString
    MAX-ACCESS  read-write
    STATUS      current
    DESCRIPTION
	"The second output name of slave4"
    ::= { slave4OutputCurrentValue 42}


-------------------------------slave4 output current Min------------------------			
slave4OutputCurrentMin OBJECT IDENTIFIER ::= { slave4OutputCurrent 2}	

slave4OutputCurrentMinOne OBJECT-TYPE
    SYNTAX      DisplayString
    MAX-ACCESS  read-write
    STATUS      current
    DESCRIPTION
	"The first output Min. current alarm value of slave4"
    ::= { slave4OutputCurrentMin 1}

slave4OutputCurrentMinTwo OBJECT-TYPE
    SYNTAX      DisplayString
    MAX-ACCESS  read-write
    STATUS      current
    DESCRIPTION
	"The second output Min. current alarm value of slave4"
    ::= { slave4OutputCurrentMin 2}

slave4OutputCurrentMinThree OBJECT-TYPE
    SYNTAX      DisplayString
    MAX-ACCESS  read-write
    STATUS      current
    DESCRIPTION
	"The second output Min. current alarm value of slave4"
    ::= { slave4OutputCurrentMin 3}

slave4OutputCurrentMinFour OBJECT-TYPE
    SYNTAX      DisplayString
    MAX-ACCESS  read-write
    STATUS      current
    DESCRIPTION
	"The second output Min. current alarm value of slave4"
    ::= { slave4OutputCurrentMin 4}

slave4OutputCurrentMinFive OBJECT-TYPE
    SYNTAX      DisplayString
    MAX-ACCESS  read-write
    STATUS      current
    DESCRIPTION
	"The second output Min. current alarm value of slave4"
    ::= { slave4OutputCurrentMin 5}

slave4OutputCurrentMinSix OBJECT-TYPE
    SYNTAX      DisplayString
    MAX-ACCESS  read-write
    STATUS      current
    DESCRIPTION
	"The second output Min. current alarm value of slave4"
    ::= { slave4OutputCurrentMin 6}

slave4OutputCurrentMinSeven OBJECT-TYPE
    SYNTAX      DisplayString
    MAX-ACCESS  read-write
    STATUS      current
    DESCRIPTION
	"The second output Min. current alarm value of slave4"
    ::= { slave4OutputCurrentMin 7}

slave4OutputCurrentMinEight OBJECT-TYPE
    SYNTAX      DisplayString
    MAX-ACCESS  read-write
    STATUS      current
    DESCRIPTION
	"The second output Min. current alarm value of slave4"
    ::= { slave4OutputCurrentMin 8}

slave4OutputCurrentMinNine OBJECT-TYPE
    SYNTAX      DisplayString
    MAX-ACCESS  read-write
    STATUS      current
    DESCRIPTION
	"The second output Min. current alarm value of slave4"
    ::= { slave4OutputCurrentMin 9}

slave4OutputCurrentMinTen OBJECT-TYPE
    SYNTAX      DisplayString
    MAX-ACCESS  read-write
    STATUS      current
    DESCRIPTION
	"The second output Min. current alarm value of slave4"
    ::= { slave4OutputCurrentMin 10}

slave4OutputCurrentMinEleven OBJECT-TYPE
    SYNTAX      DisplayString
    MAX-ACCESS  read-write
    STATUS      current
    DESCRIPTION
	"The second output Min. current alarm value of slave4"
    ::= { slave4OutputCurrentMin 11}

slave4OutputCurrentMinTwel OBJECT-TYPE
    SYNTAX      DisplayString
    MAX-ACCESS  read-write
    STATUS      current
    DESCRIPTION
	"The second output Min. current alarm value of slave4"
    ::= { slave4OutputCurrentMin 12}

slave4OutputCurrentMinThirteen OBJECT-TYPE
    SYNTAX      DisplayString
    MAX-ACCESS  read-write
    STATUS      current
    DESCRIPTION
	"The second output Min. current alarm value of slave4"
    ::= { slave4OutputCurrentMin 13}

slave4OutputCurrentMinFourteen OBJECT-TYPE
    SYNTAX      DisplayString
    MAX-ACCESS  read-write
    STATUS      current
    DESCRIPTION
	"The second output Min. current alarm value of slave4"
    ::= { slave4OutputCurrentMin 14}

slave4OutputCurrentMinFifteen OBJECT-TYPE
    SYNTAX      DisplayString
    MAX-ACCESS  read-write
    STATUS      current
    DESCRIPTION
	"The second output Min. current alarm value of slave4"
    ::= { slave4OutputCurrentMin 15}

slave4OutputCurrentMinSixteen OBJECT-TYPE
    SYNTAX      DisplayString
    MAX-ACCESS  read-write
    STATUS      current
    DESCRIPTION
	"The second output Min. current alarm value of slave4"
    ::= { slave4OutputCurrentMin 16}

slave4OutputCurrentMinSeventeen OBJECT-TYPE
    SYNTAX      DisplayString
    MAX-ACCESS  read-write
    STATUS      current
    DESCRIPTION
	"The second output Min. current alarm value of slave4"
    ::= { slave4OutputCurrentMin 17}

slave4OutputCurrentMinEighteen OBJECT-TYPE
    SYNTAX      DisplayString
    MAX-ACCESS  read-write
    STATUS      current
    DESCRIPTION
	"The second output Min. current alarm value of slave4"
    ::= { slave4OutputCurrentMin 18}
	
slave4OutputCurrentMinNineteen OBJECT-TYPE
    SYNTAX      DisplayString
    MAX-ACCESS  read-write
    STATUS      current
    DESCRIPTION
	"The second output Min. current alarm value of slave4"
    ::= { slave4OutputCurrentMin 19}
	
slave4OutputCurrentMintwenty OBJECT-TYPE
    SYNTAX      DisplayString
    MAX-ACCESS  read-write
    STATUS      current
    DESCRIPTION
	"The second output Min. current alarm value of slave4"
    ::= { slave4OutputCurrentMin 20}
	
slave4OutputCurrentMinTwentyone OBJECT-TYPE
    SYNTAX      DisplayString
    MAX-ACCESS  read-write
    STATUS      current
    DESCRIPTION
	"The second output Min. current alarm value of slave4"
    ::= { slave4OutputCurrentMin 21}
	
slave4OutputCurrentMinTwentyonetwo OBJECT-TYPE
    SYNTAX      DisplayString
    MAX-ACCESS  read-write
    STATUS      current
    DESCRIPTION
	"The second output Min. current alarm value of slave4"
    ::= { slave4OutputCurrentMin 22}
	
slave4OutputCurrentMinTwentythree OBJECT-TYPE
    SYNTAX      DisplayString
    MAX-ACCESS  read-write
    STATUS      current
    DESCRIPTION
	"The second output Min. current alarm value of slave4"
    ::= { slave4OutputCurrentMin 23}
	
slave4OutputCurrentMinTwentyfour OBJECT-TYPE
    SYNTAX      DisplayString
    MAX-ACCESS  read-write
    STATUS      current
    DESCRIPTION
	"The second output Min. current alarm value of slave4"
    ::= { slave4OutputCurrentMin 24}
	
slave4OutputCurrentMinTwentyfive OBJECT-TYPE
    SYNTAX      DisplayString
    MAX-ACCESS  read-write
    STATUS      current
    DESCRIPTION
	"The second output Min. current alarm value of slave4"
    ::= { slave4OutputCurrentMin 25}
	
slave4OutputCurrentMinTwentysix OBJECT-TYPE
    SYNTAX      DisplayString
    MAX-ACCESS  read-write
    STATUS      current
    DESCRIPTION
	"The second output Min. current alarm value of slave4"
    ::= { slave4OutputCurrentMin 26}
	
slave4OutputCurrentMinTwentyseven OBJECT-TYPE
    SYNTAX      DisplayString
    MAX-ACCESS  read-write
    STATUS      current
    DESCRIPTION
	"The second output Min. current alarm value of slave4"
    ::= { slave4OutputCurrentMin 27}
	
slave4OutputCurrentMinTwentyeight OBJECT-TYPE
    SYNTAX      DisplayString
    MAX-ACCESS  read-write
    STATUS      current
    DESCRIPTION
	"The second output Min. current alarm value of slave4"
    ::= { slave4OutputCurrentMin 28}	
slave4OutputCurrentMinTwentynine OBJECT-TYPE
    SYNTAX      DisplayString
    MAX-ACCESS  read-write
    STATUS      current
    DESCRIPTION
	"The second output Min. current alarm value of slave4"
    ::= { slave4OutputCurrentMin 29}
	
slave4OutputCurrentMinThirty OBJECT-TYPE
    SYNTAX      DisplayString
    MAX-ACCESS  read-write
    STATUS      current
    DESCRIPTION
	"The second output Min. current alarm value of slave4"
    ::= { slave4OutputCurrentMin 30}
	
slave4OutputCurrentMinThirtyone OBJECT-TYPE
    SYNTAX      DisplayString
    MAX-ACCESS  read-write
    STATUS      current
    DESCRIPTION
	"The second output Min. current alarm value of slave4"
    ::= { slave4OutputCurrentMin 31}
	
slave4OutputCurrentMinThirtytwo OBJECT-TYPE
    SYNTAX      DisplayString
    MAX-ACCESS  read-write
    STATUS      current
    DESCRIPTION
	"The second output Min. current alarm value of slave4"
    ::= { slave4OutputCurrentMin 32}
	
slave4OutputCurrentMinThirtythree OBJECT-TYPE
    SYNTAX      DisplayString
    MAX-ACCESS  read-write
    STATUS      current
    DESCRIPTION
	"The second output Min. current alarm value of slave4"
    ::= { slave4OutputCurrentMin 33}
	
slave4OutputCurrentMinThirtyfour OBJECT-TYPE
    SYNTAX      DisplayString
    MAX-ACCESS  read-write
    STATUS      current
    DESCRIPTION
	"The second output Min. current alarm value of slave4"
    ::= { slave4OutputCurrentMin 34}
	
slave4OutputCurrentMinThirtyfive OBJECT-TYPE
    SYNTAX      DisplayString
    MAX-ACCESS  read-write
    STATUS      current
    DESCRIPTION
	"The second output Min. current alarm value of slave4"
    ::= { slave4OutputCurrentMin 35}
	
slave4OutputCurrentMinThirtysix OBJECT-TYPE
    SYNTAX      DisplayString
    MAX-ACCESS  read-write
    STATUS      current
    DESCRIPTION
	"The second output Min. current alarm value of slave4"
    ::= { slave4OutputCurrentMin 36}
	
slave4OutputCurrentMinThirtyseven OBJECT-TYPE
    SYNTAX      DisplayString
    MAX-ACCESS  read-write
    STATUS      current
    DESCRIPTION
	"The second output Min. current alarm value of slave4"
    ::= { slave4OutputCurrentMin 37}
	
slave4OutputCurrentMinThirtyeight OBJECT-TYPE
    SYNTAX      DisplayString
    MAX-ACCESS  read-write
    STATUS      current
    DESCRIPTION
	"The second output Min. current alarm value of slave4"
    ::= { slave4OutputCurrentMin 38}
	
slave4OutputCurrentMinThirtynine OBJECT-TYPE
    SYNTAX      DisplayString
    MAX-ACCESS  read-write
    STATUS      current
    DESCRIPTION
	"The second output Min. current alarm value of slave4"
    ::= { slave4OutputCurrentMin 39}
	
slave4OutputCurrentMinFourty OBJECT-TYPE
    SYNTAX      DisplayString
    MAX-ACCESS  read-write
    STATUS      current
    DESCRIPTION
	"The second output Min. current alarm value of slave4"
    ::= { slave4OutputCurrentMin 40}
	
slave4OutputCurrentMinFourtyone OBJECT-TYPE
    SYNTAX      DisplayString
    MAX-ACCESS  read-write
    STATUS      current
    DESCRIPTION
	"The second output Min. current alarm value of slave4"
    ::= { slave4OutputCurrentMin 41}
	
slave4OutputCurrentMinFourtytwo OBJECT-TYPE
    SYNTAX      DisplayString
    MAX-ACCESS  read-write
    STATUS      current
    DESCRIPTION
	"The second output Min. current alarm value of slave4"
    ::= { slave4OutputCurrentMin 42}


------------------------slave4 output current Min critical----------------			
slave4OutputCurrentMinCritical OBJECT IDENTIFIER ::= { slave4OutputCurrent 3}	

slave4OutputCurrentMinCriticalOne OBJECT-TYPE
    SYNTAX      DisplayString
    MAX-ACCESS  read-write
    STATUS      current
    DESCRIPTION
	"The first output Min. current warning value of slave4"
    ::= { slave4OutputCurrentMinCritical 1}

slave4OutputCurrentMinCriticalTwo OBJECT-TYPE
    SYNTAX      DisplayString
    MAX-ACCESS  read-write
    STATUS      current
    DESCRIPTION
	"The second output Min. current warning value of slave4"
    ::= { slave4OutputCurrentMinCritical 2}

slave4OutputCurrentMinCriticalThree OBJECT-TYPE
    SYNTAX      DisplayString
    MAX-ACCESS  read-write
    STATUS      current
    DESCRIPTION
	"The second output Min. current warning value of slave4"
    ::= { slave4OutputCurrentMinCritical 3}

slave4OutputCurrentMinCriticalFour OBJECT-TYPE
    SYNTAX      DisplayString
    MAX-ACCESS  read-write
    STATUS      current
    DESCRIPTION
	"The second output Min. current warning value of slave4"
    ::= { slave4OutputCurrentMinCritical 4}

slave4OutputCurrentMinCriticalFive OBJECT-TYPE
    SYNTAX      DisplayString
    MAX-ACCESS  read-write
    STATUS      current
    DESCRIPTION
	"The second output Min. current warning value of slave4"
    ::= { slave4OutputCurrentMinCritical 5}

slave4OutputCurrentMinCriticalSix OBJECT-TYPE
    SYNTAX      DisplayString
    MAX-ACCESS  read-write
    STATUS      current
    DESCRIPTION
	"The second output Min. current warning value of slave4"
    ::= { slave4OutputCurrentMinCritical 6}

slave4OutputCurrentMinCriticalSeven OBJECT-TYPE
    SYNTAX      DisplayString
    MAX-ACCESS  read-write
    STATUS      current
    DESCRIPTION
	"The second output Min. current warning value of slave4"
    ::= { slave4OutputCurrentMinCritical 7}

slave4OutputCurrentMinCriticalEight OBJECT-TYPE
    SYNTAX      DisplayString
    MAX-ACCESS  read-write
    STATUS      current
    DESCRIPTION
	"The second output Min. current warning value of slave4"
    ::= { slave4OutputCurrentMinCritical 8}

slave4OutputCurrentMinCriticalNine OBJECT-TYPE
    SYNTAX      DisplayString
    MAX-ACCESS  read-write
    STATUS      current
    DESCRIPTION
	"The second output Min. current warning value of slave4"
    ::= { slave4OutputCurrentMinCritical 9}

slave4OutputCurrentMinCriticalTen OBJECT-TYPE
    SYNTAX      DisplayString
    MAX-ACCESS  read-write
    STATUS      current
    DESCRIPTION
	"The second output Min. current warning value of slave4"
    ::= { slave4OutputCurrentMinCritical 10}

slave4OutputCurrentMinCriticalEleven OBJECT-TYPE
    SYNTAX      DisplayString
    MAX-ACCESS  read-write
    STATUS      current
    DESCRIPTION
	"The second output Min. current warning value of slave4"
    ::= { slave4OutputCurrentMinCritical 11}

slave4OutputCurrentMinCriticalTwel OBJECT-TYPE
    SYNTAX      DisplayString
    MAX-ACCESS  read-write
    STATUS      current
    DESCRIPTION
	"The second output Min. current warning value of slave4"
    ::= { slave4OutputCurrentMinCritical 12}

slave4OutputCurrentMinCriticalThirteen OBJECT-TYPE
    SYNTAX      DisplayString
    MAX-ACCESS  read-write
    STATUS      current
    DESCRIPTION
	"The second output Min. current warning value of slave4"
    ::= { slave4OutputCurrentMinCritical 13}

slave4OutputCurrentMinCriticalFourteen OBJECT-TYPE
    SYNTAX      DisplayString
    MAX-ACCESS  read-write
    STATUS      current
    DESCRIPTION
	"The second output Min. current warning value of slave4"
    ::= { slave4OutputCurrentMinCritical 14}

slave4OutputCurrentMinCriticalFifteen OBJECT-TYPE
    SYNTAX      DisplayString
    MAX-ACCESS  read-write
    STATUS      current
    DESCRIPTION
	"The second output Min. current warning value of slave4"
    ::= { slave4OutputCurrentMinCritical 15}

slave4OutputCurrentMinCriticalSixteen OBJECT-TYPE
    SYNTAX      DisplayString
    MAX-ACCESS  read-write
    STATUS      current
    DESCRIPTION
	"The second output Min. current warning value of slave4"
    ::= { slave4OutputCurrentMinCritical 16}

slave4OutputCurrentMinCriticalSeventeen OBJECT-TYPE
    SYNTAX      DisplayString
    MAX-ACCESS  read-write
    STATUS      current
    DESCRIPTION
	"The second output Min. current warning value of slave4"
    ::= { slave4OutputCurrentMinCritical 17}

slave4OutputCurrentMinCriticalEighteen OBJECT-TYPE
    SYNTAX      DisplayString
    MAX-ACCESS  read-write
    STATUS      current
    DESCRIPTION
	"The second output Min. current warning value of slave4"
    ::= { slave4OutputCurrentMinCritical 18}
	
slave4OutputCurrentMinCriticalNineteen OBJECT-TYPE
    SYNTAX      DisplayString
    MAX-ACCESS  read-write
    STATUS      current
    DESCRIPTION
	"The second output Min. current warning value of slave4"
    ::= { slave4OutputCurrentMinCritical 19}
	
slave4OutputCurrentMinCriticaltwenty OBJECT-TYPE
    SYNTAX      DisplayString
    MAX-ACCESS  read-write
    STATUS      current
    DESCRIPTION
	"The second output Min. current warning value of slave4"
    ::= { slave4OutputCurrentMinCritical 20}
	
slave4OutputCurrentMinCriticalTwentyone OBJECT-TYPE
    SYNTAX      DisplayString
    MAX-ACCESS  read-write
    STATUS      current
    DESCRIPTION
	"The second output Min. current warning value of slave4"
    ::= { slave4OutputCurrentMinCritical 21}
	
slave4OutputCurrentMinCriticalTwentyonetwo OBJECT-TYPE
    SYNTAX      DisplayString
    MAX-ACCESS  read-write
    STATUS      current
    DESCRIPTION
	"The second output Min. current warning value of slave4"
    ::= { slave4OutputCurrentMinCritical 22}
	
slave4OutputCurrentMinCriticalTwentythree OBJECT-TYPE
    SYNTAX      DisplayString
    MAX-ACCESS  read-write
    STATUS      current
    DESCRIPTION
	"The second output Min. current warning value of slave4"
    ::= { slave4OutputCurrentMinCritical 23}
	
slave4OutputCurrentMinCriticalTwentyfour OBJECT-TYPE
    SYNTAX      DisplayString
    MAX-ACCESS  read-write
    STATUS      current
    DESCRIPTION
	"The second output Min. current warning value of slave4"
    ::= { slave4OutputCurrentMinCritical 24}
	
slave4OutputCurrentMinCriticalTwentyfive OBJECT-TYPE
    SYNTAX      DisplayString
    MAX-ACCESS  read-write
    STATUS      current
    DESCRIPTION
	"The second output Min. current warning value of slave4"
    ::= { slave4OutputCurrentMinCritical 25}
	
slave4OutputCurrentMinCriticalTwentysix OBJECT-TYPE
    SYNTAX      DisplayString
    MAX-ACCESS  read-write
    STATUS      current
    DESCRIPTION
	"The second output Min. current warning value of slave4"
    ::= { slave4OutputCurrentMinCritical 26}
	
slave4OutputCurrentMinCriticalTwentyseven OBJECT-TYPE
    SYNTAX      DisplayString
    MAX-ACCESS  read-write
    STATUS      current
    DESCRIPTION
	"The second output Min. current warning value of slave4"
    ::= { slave4OutputCurrentMinCritical 27}
	
slave4OutputCurrentMinCriticalTwentyeight OBJECT-TYPE
    SYNTAX      DisplayString
    MAX-ACCESS  read-write
    STATUS      current
    DESCRIPTION
	"The second output Min. current warning value of slave4"
    ::= { slave4OutputCurrentMinCritical 28}	
slave4OutputCurrentMinCriticalTwentynine OBJECT-TYPE
    SYNTAX      DisplayString
    MAX-ACCESS  read-write
    STATUS      current
    DESCRIPTION
	"The second output Min. current warning value of slave4"
    ::= { slave4OutputCurrentMinCritical 29}
	
slave4OutputCurrentMinCriticalThirty OBJECT-TYPE
    SYNTAX      DisplayString
    MAX-ACCESS  read-write
    STATUS      current
    DESCRIPTION
	"The second output Min. current warning value of slave4"
    ::= { slave4OutputCurrentMinCritical 30}
	
slave4OutputCurrentMinCriticalThirtyone OBJECT-TYPE
    SYNTAX      DisplayString
    MAX-ACCESS  read-write
    STATUS      current
    DESCRIPTION
	"The second output Min. current warning value of slave4"
    ::= { slave4OutputCurrentMinCritical 31}
	
slave4OutputCurrentMinCriticalThirtytwo OBJECT-TYPE
    SYNTAX      DisplayString
    MAX-ACCESS  read-write
    STATUS      current
    DESCRIPTION
	"The second output Min. current warning value of slave4"
    ::= { slave4OutputCurrentMinCritical 32}
	
slave4OutputCurrentMinCriticalThirtythree OBJECT-TYPE
    SYNTAX      DisplayString
    MAX-ACCESS  read-write
    STATUS      current
    DESCRIPTION
	"The second output Min. current warning value of slave4"
    ::= { slave4OutputCurrentMinCritical 33}
	
slave4OutputCurrentMinCriticalThirtyfour OBJECT-TYPE
    SYNTAX      DisplayString
    MAX-ACCESS  read-write
    STATUS      current
    DESCRIPTION
	"The second output Min. current warning value of slave4"
    ::= { slave4OutputCurrentMinCritical 34}
	
slave4OutputCurrentMinCriticalThirtyfive OBJECT-TYPE
    SYNTAX      DisplayString
    MAX-ACCESS  read-write
    STATUS      current
    DESCRIPTION
	"The second output Min. current warning value of slave4"
    ::= { slave4OutputCurrentMinCritical 35}
	
slave4OutputCurrentMinCriticalThirtysix OBJECT-TYPE
    SYNTAX      DisplayString
    MAX-ACCESS  read-write
    STATUS      current
    DESCRIPTION
	"The second output Min. current warning value of slave4"
    ::= { slave4OutputCurrentMinCritical 36}
	
slave4OutputCurrentMinCriticalThirtyseven OBJECT-TYPE
    SYNTAX      DisplayString
    MAX-ACCESS  read-write
    STATUS      current
    DESCRIPTION
	"The second output Min. current warning value of slave4"
    ::= { slave4OutputCurrentMinCritical 37}
	
slave4OutputCurrentMinCriticalThirtyeight OBJECT-TYPE
    SYNTAX      DisplayString
    MAX-ACCESS  read-write
    STATUS      current
    DESCRIPTION
	"The second output Min. current warning value of slave4"
    ::= { slave4OutputCurrentMinCritical 38}
	
slave4OutputCurrentMinCriticalThirtynine OBJECT-TYPE
    SYNTAX      DisplayString
    MAX-ACCESS  read-write
    STATUS      current
    DESCRIPTION
	"The second output Min. current warning value of slave4"
    ::= { slave4OutputCurrentMinCritical 39}
	
slave4OutputCurrentMinCriticalFourty OBJECT-TYPE
    SYNTAX      DisplayString
    MAX-ACCESS  read-write
    STATUS      current
    DESCRIPTION
	"The second output Min. current warning value of slave4"
    ::= { slave4OutputCurrentMinCritical 40}
	
slave4OutputCurrentMinCriticalFourtyone OBJECT-TYPE
    SYNTAX      DisplayString
    MAX-ACCESS  read-write
    STATUS      current
    DESCRIPTION
	"The second output Min. current warning value of slave4"
    ::= { slave4OutputCurrentMinCritical 41}
	
slave4OutputCurrentMinCriticalFourtytwo OBJECT-TYPE
    SYNTAX      DisplayString
    MAX-ACCESS  read-write
    STATUS      current
    DESCRIPTION
	"The second output Min. current warning value of slave4"
    ::= { slave4OutputCurrentMinCritical 42}
	
	
------------------------slave4 output current Max critical----------------			
slave4OutputCurrentMaxCritical OBJECT IDENTIFIER ::= { slave4OutputCurrent 4}	

slave4OutputCurrentMaxCriticalOne OBJECT-TYPE
    SYNTAX      DisplayString
    MAX-ACCESS  read-write
    STATUS      current
    DESCRIPTION
	"The first output Max. current warning value of slave4"
    ::= { slave4OutputCurrentMaxCritical 1}

slave4OutputCurrentMaxCriticalTwo OBJECT-TYPE
    SYNTAX      DisplayString
    MAX-ACCESS  read-write
    STATUS      current
    DESCRIPTION
	"The second output Max. current warning value of slave4"
    ::= { slave4OutputCurrentMaxCritical 2}

slave4OutputCurrentMaxCriticalThree OBJECT-TYPE
    SYNTAX      DisplayString
    MAX-ACCESS  read-write
    STATUS      current
    DESCRIPTION
	"The second output Max. current warning value of slave4"
    ::= { slave4OutputCurrentMaxCritical 3}

slave4OutputCurrentMaxCriticalFour OBJECT-TYPE
    SYNTAX      DisplayString
    MAX-ACCESS  read-write
    STATUS      current
    DESCRIPTION
	"The second output Max. current warning value of slave4"
    ::= { slave4OutputCurrentMaxCritical 4}

slave4OutputCurrentMaxCriticalFive OBJECT-TYPE
    SYNTAX      DisplayString
    MAX-ACCESS  read-write
    STATUS      current
    DESCRIPTION
	"The second output Max. current warning value of slave4"
    ::= { slave4OutputCurrentMaxCritical 5}

slave4OutputCurrentMaxCriticalSix OBJECT-TYPE
    SYNTAX      DisplayString
    MAX-ACCESS  read-write
    STATUS      current
    DESCRIPTION
	"The second output Max. current warning value of slave4"
    ::= { slave4OutputCurrentMaxCritical 6}

slave4OutputCurrentMaxCriticalSeven OBJECT-TYPE
    SYNTAX      DisplayString
    MAX-ACCESS  read-write
    STATUS      current
    DESCRIPTION
	"The second output Max. current warning value of slave4"
    ::= { slave4OutputCurrentMaxCritical 7}

slave4OutputCurrentMaxCriticalEight OBJECT-TYPE
    SYNTAX      DisplayString
    MAX-ACCESS  read-write
    STATUS      current
    DESCRIPTION
	"The second output Max. current warning value of slave4"
    ::= { slave4OutputCurrentMaxCritical 8}

slave4OutputCurrentMaxCriticalNine OBJECT-TYPE
    SYNTAX      DisplayString
    MAX-ACCESS  read-write
    STATUS      current
    DESCRIPTION
	"The second output Max. current warning value of slave4"
    ::= { slave4OutputCurrentMaxCritical 9}

slave4OutputCurrentMaxCriticalTen OBJECT-TYPE
    SYNTAX      DisplayString
    MAX-ACCESS  read-write
    STATUS      current
    DESCRIPTION
	"The second output Max. current warning value of slave4"
    ::= { slave4OutputCurrentMaxCritical 10}

slave4OutputCurrentMaxCriticalEleven OBJECT-TYPE
    SYNTAX      DisplayString
    MAX-ACCESS  read-write
    STATUS      current
    DESCRIPTION
	"The second output Max. current warning value of slave4"
    ::= { slave4OutputCurrentMaxCritical 11}

slave4OutputCurrentMaxCriticalTwel OBJECT-TYPE
    SYNTAX      DisplayString
    MAX-ACCESS  read-write
    STATUS      current
    DESCRIPTION
	"The second output Max. current warning value of slave4"
    ::= { slave4OutputCurrentMaxCritical 12}

slave4OutputCurrentMaxCriticalThirteen OBJECT-TYPE
    SYNTAX      DisplayString
    MAX-ACCESS  read-write
    STATUS      current
    DESCRIPTION
	"The second output Max. current warning value of slave4"
    ::= { slave4OutputCurrentMaxCritical 13}

slave4OutputCurrentMaxCriticalFourteen OBJECT-TYPE
    SYNTAX      DisplayString
    MAX-ACCESS  read-write
    STATUS      current
    DESCRIPTION
	"The second output Max. current warning value of slave4"
    ::= { slave4OutputCurrentMaxCritical 14}

slave4OutputCurrentMaxCriticalFifteen OBJECT-TYPE
    SYNTAX      DisplayString
    MAX-ACCESS  read-write
    STATUS      current
    DESCRIPTION
	"The second output Max. current warning value of slave4"
    ::= { slave4OutputCurrentMaxCritical 15}

slave4OutputCurrentMaxCriticalSixteen OBJECT-TYPE
    SYNTAX      DisplayString
    MAX-ACCESS  read-write
    STATUS      current
    DESCRIPTION
	"The second output Max. current warning value of slave4"
    ::= { slave4OutputCurrentMaxCritical 16}

slave4OutputCurrentMaxCriticalSeventeen OBJECT-TYPE
    SYNTAX      DisplayString
    MAX-ACCESS  read-write
    STATUS      current
    DESCRIPTION
	"The second output Max. current warning value of slave4"
    ::= { slave4OutputCurrentMaxCritical 17}

slave4OutputCurrentMaxCriticalEighteen OBJECT-TYPE
    SYNTAX      DisplayString
    MAX-ACCESS  read-write
    STATUS      current
    DESCRIPTION
	"The second output Max. current warning value of slave4"
    ::= { slave4OutputCurrentMaxCritical 18}
	
slave4OutputCurrentMaxCriticalNineteen OBJECT-TYPE
    SYNTAX      DisplayString
    MAX-ACCESS  read-write
    STATUS      current
    DESCRIPTION
	"The second output Max. current warning value of slave4"
    ::= { slave4OutputCurrentMaxCritical 19}
	
slave4OutputCurrentMaxCriticaltwenty OBJECT-TYPE
    SYNTAX      DisplayString
    MAX-ACCESS  read-write
    STATUS      current
    DESCRIPTION
	"The second output Max. current warning value of slave4"
    ::= { slave4OutputCurrentMaxCritical 20}
	
slave4OutputCurrentMaxCriticalTwentyone OBJECT-TYPE
    SYNTAX      DisplayString
    MAX-ACCESS  read-write
    STATUS      current
    DESCRIPTION
	"The second output Max. current warning value of slave4"
    ::= { slave4OutputCurrentMaxCritical 21}
	
slave4OutputCurrentMaxCriticalTwentyonetwo OBJECT-TYPE
    SYNTAX      DisplayString
    MAX-ACCESS  read-write
    STATUS      current
    DESCRIPTION
	"The second output Max. current warning value of slave4"
    ::= { slave4OutputCurrentMaxCritical 22}
	
slave4OutputCurrentMaxCriticalTwentythree OBJECT-TYPE
    SYNTAX      DisplayString
    MAX-ACCESS  read-write
    STATUS      current
    DESCRIPTION
	"The second output Max. current warning value of slave4"
    ::= { slave4OutputCurrentMaxCritical 23}
	
slave4OutputCurrentMaxCriticalTwentyfour OBJECT-TYPE
    SYNTAX      DisplayString
    MAX-ACCESS  read-write
    STATUS      current
    DESCRIPTION
	"The second output Max. current warning value of slave4"
    ::= { slave4OutputCurrentMaxCritical 24}
	
slave4OutputCurrentMaxCriticalTwentyfive OBJECT-TYPE
    SYNTAX      DisplayString
    MAX-ACCESS  read-write
    STATUS      current
    DESCRIPTION
	"The second output Max. current warning value of slave4"
    ::= { slave4OutputCurrentMaxCritical 25}
	
slave4OutputCurrentMaxCriticalTwentysix OBJECT-TYPE
    SYNTAX      DisplayString
    MAX-ACCESS  read-write
    STATUS      current
    DESCRIPTION
	"The second output Max. current warning value of slave4"
    ::= { slave4OutputCurrentMaxCritical 26}
	
slave4OutputCurrentMaxCriticalTwentyseven OBJECT-TYPE
    SYNTAX      DisplayString
    MAX-ACCESS  read-write
    STATUS      current
    DESCRIPTION
	"The second output Max. current warning value of slave4"
    ::= { slave4OutputCurrentMaxCritical 27}
	
slave4OutputCurrentMaxCriticalTwentyeight OBJECT-TYPE
    SYNTAX      DisplayString
    MAX-ACCESS  read-write
    STATUS      current
    DESCRIPTION
	"The second output Max. current warning value of slave4"
    ::= { slave4OutputCurrentMaxCritical 28}	
slave4OutputCurrentMaxCriticalTwentynine OBJECT-TYPE
    SYNTAX      DisplayString
    MAX-ACCESS  read-write
    STATUS      current
    DESCRIPTION
	"The second output Max. current warning value of slave4"
    ::= { slave4OutputCurrentMaxCritical 29}
	
slave4OutputCurrentMaxCriticalThirty OBJECT-TYPE
    SYNTAX      DisplayString
    MAX-ACCESS  read-write
    STATUS      current
    DESCRIPTION
	"The second output Max. current warning value of slave4"
    ::= { slave4OutputCurrentMaxCritical 30}
	
slave4OutputCurrentMaxCriticalThirtyone OBJECT-TYPE
    SYNTAX      DisplayString
    MAX-ACCESS  read-write
    STATUS      current
    DESCRIPTION
	"The second output Max. current warning value of slave4"
    ::= { slave4OutputCurrentMaxCritical 31}
	
slave4OutputCurrentMaxCriticalThirtytwo OBJECT-TYPE
    SYNTAX      DisplayString
    MAX-ACCESS  read-write
    STATUS      current
    DESCRIPTION
	"The second output Max. current warning value of slave4"
    ::= { slave4OutputCurrentMaxCritical 32}
	
slave4OutputCurrentMaxCriticalThirtythree OBJECT-TYPE
    SYNTAX      DisplayString
    MAX-ACCESS  read-write
    STATUS      current
    DESCRIPTION
	"The second output Max. current warning value of slave4"
    ::= { slave4OutputCurrentMaxCritical 33}
	
slave4OutputCurrentMaxCriticalThirtyfour OBJECT-TYPE
    SYNTAX      DisplayString
    MAX-ACCESS  read-write
    STATUS      current
    DESCRIPTION
	"The second output Max. current warning value of slave4"
    ::= { slave4OutputCurrentMaxCritical 34}
	
slave4OutputCurrentMaxCriticalThirtyfive OBJECT-TYPE
    SYNTAX      DisplayString
    MAX-ACCESS  read-write
    STATUS      current
    DESCRIPTION
	"The second output Max. current warning value of slave4"
    ::= { slave4OutputCurrentMaxCritical 35}
	
slave4OutputCurrentMaxCriticalThirtysix OBJECT-TYPE
    SYNTAX      DisplayString
    MAX-ACCESS  read-write
    STATUS      current
    DESCRIPTION
	"The second output Max. current warning value of slave4"
    ::= { slave4OutputCurrentMaxCritical 36}
	
slave4OutputCurrentMaxCriticalThirtyseven OBJECT-TYPE
    SYNTAX      DisplayString
    MAX-ACCESS  read-write
    STATUS      current
    DESCRIPTION
	"The second output Max. current warning value of slave4"
    ::= { slave4OutputCurrentMaxCritical 37}
	
slave4OutputCurrentMaxCriticalThirtyeight OBJECT-TYPE
    SYNTAX      DisplayString
    MAX-ACCESS  read-write
    STATUS      current
    DESCRIPTION
	"The second output Max. current warning value of slave4"
    ::= { slave4OutputCurrentMaxCritical 38}
	
slave4OutputCurrentMaxCriticalThirtynine OBJECT-TYPE
    SYNTAX      DisplayString
    MAX-ACCESS  read-write
    STATUS      current
    DESCRIPTION
	"The second output Max. current warning value of slave4"
    ::= { slave4OutputCurrentMaxCritical 39}
	
slave4OutputCurrentMaxCriticalFourty OBJECT-TYPE
    SYNTAX      DisplayString
    MAX-ACCESS  read-write
    STATUS      current
    DESCRIPTION
	"The second output Max. current warning value of slave4"
    ::= { slave4OutputCurrentMaxCritical 40}
	
slave4OutputCurrentMaxCriticalFourtyone OBJECT-TYPE
    SYNTAX      DisplayString
    MAX-ACCESS  read-write
    STATUS      current
    DESCRIPTION
	"The second output Max. current warning value of slave4"
    ::= { slave4OutputCurrentMaxCritical 41}
	
slave4OutputCurrentMaxCriticalFourtytwo OBJECT-TYPE
    SYNTAX      DisplayString
    MAX-ACCESS  read-write
    STATUS      current
    DESCRIPTION
	"The second output Max. current warning value of slave4"
    ::= { slave4OutputCurrentMaxCritical 42}
	
	
------------------------slave4 output current Max----------------			
slave4OutputCurrentMax OBJECT IDENTIFIER ::= { slave4OutputCurrent 5}
	
slave4OutputCurrentMaxOne OBJECT-TYPE
    SYNTAX      DisplayString
    MAX-ACCESS  read-write
    STATUS      current
    DESCRIPTION
	"The first output Max. current alarm value of slave4"
    ::= { slave4OutputCurrentMax 1}

slave4OutputCurrentMaxTwo OBJECT-TYPE
    SYNTAX      DisplayString
    MAX-ACCESS  read-write
    STATUS      current
    DESCRIPTION
	"The second output Max. current alarm value of slave4"
    ::= { slave4OutputCurrentMax 2}

slave4OutputCurrentMaxThree OBJECT-TYPE
    SYNTAX      DisplayString
    MAX-ACCESS  read-write
    STATUS      current
    DESCRIPTION
	"The second output Max. current alarm value of slave4"
    ::= { slave4OutputCurrentMax 3}

slave4OutputCurrentMaxFour OBJECT-TYPE
    SYNTAX      DisplayString
    MAX-ACCESS  read-write
    STATUS      current
    DESCRIPTION
	"The second output Max. current alarm value of slave4"
    ::= { slave4OutputCurrentMax 4}

slave4OutputCurrentMaxFive OBJECT-TYPE
    SYNTAX      DisplayString
    MAX-ACCESS  read-write
    STATUS      current
    DESCRIPTION
	"The second output Max. current alarm value of slave4"
    ::= { slave4OutputCurrentMax 5}

slave4OutputCurrentMaxSix OBJECT-TYPE
    SYNTAX      DisplayString
    MAX-ACCESS  read-write
    STATUS      current
    DESCRIPTION
	"The second output Max. current alarm value of slave4"
    ::= { slave4OutputCurrentMax 6}

slave4OutputCurrentMaxSeven OBJECT-TYPE
    SYNTAX      DisplayString
    MAX-ACCESS  read-write
    STATUS      current
    DESCRIPTION
	"The second output Max. current alarm value of slave4"
    ::= { slave4OutputCurrentMax 7}

slave4OutputCurrentMaxEight OBJECT-TYPE
    SYNTAX      DisplayString
    MAX-ACCESS  read-write
    STATUS      current
    DESCRIPTION
	"The second output Max. current alarm value of slave4"
    ::= { slave4OutputCurrentMax 8}

slave4OutputCurrentMaxNine OBJECT-TYPE
    SYNTAX      DisplayString
    MAX-ACCESS  read-write
    STATUS      current
    DESCRIPTION
	"The second output Max. current alarm value of slave4"
    ::= { slave4OutputCurrentMax 9}

slave4OutputCurrentMaxTen OBJECT-TYPE
    SYNTAX      DisplayString
    MAX-ACCESS  read-write
    STATUS      current
    DESCRIPTION
	"The second output Max. current alarm value of slave4"
    ::= { slave4OutputCurrentMax 10}

slave4OutputCurrentMaxEleven OBJECT-TYPE
    SYNTAX      DisplayString
    MAX-ACCESS  read-write
    STATUS      current
    DESCRIPTION
	"The second output Max. current alarm value of slave4"
    ::= { slave4OutputCurrentMax 11}

slave4OutputCurrentMaxTwel OBJECT-TYPE
    SYNTAX      DisplayString
    MAX-ACCESS  read-write
    STATUS      current
    DESCRIPTION
	"The second output Max. current alarm value of slave4"
    ::= { slave4OutputCurrentMax 12}

slave4OutputCurrentMaxThirteen OBJECT-TYPE
    SYNTAX      DisplayString
    MAX-ACCESS  read-write
    STATUS      current
    DESCRIPTION
	"The second output Max. current alarm value of slave4"
    ::= { slave4OutputCurrentMax 13}

slave4OutputCurrentMaxFourteen OBJECT-TYPE
    SYNTAX      DisplayString
    MAX-ACCESS  read-write
    STATUS      current
    DESCRIPTION
	"The second output Max. current alarm value of slave4"
    ::= { slave4OutputCurrentMax 14}

slave4OutputCurrentMaxFifteen OBJECT-TYPE
    SYNTAX      DisplayString
    MAX-ACCESS  read-write
    STATUS      current
    DESCRIPTION
	"The second output Max. current alarm value of slave4"
    ::= { slave4OutputCurrentMax 15}

slave4OutputCurrentMaxSixteen OBJECT-TYPE
    SYNTAX      DisplayString
    MAX-ACCESS  read-write
    STATUS      current
    DESCRIPTION
	"The second output Max. current alarm value of slave4"
    ::= { slave4OutputCurrentMax 16}

slave4OutputCurrentMaxSeventeen OBJECT-TYPE
    SYNTAX      DisplayString
    MAX-ACCESS  read-write
    STATUS      current
    DESCRIPTION
	"The second output Max. current alarm value of slave4"
    ::= { slave4OutputCurrentMax 17}

slave4OutputCurrentMaxEighteen OBJECT-TYPE
    SYNTAX      DisplayString
    MAX-ACCESS  read-write
    STATUS      current
    DESCRIPTION
	"The second output Max. current alarm value of slave4"
    ::= { slave4OutputCurrentMax 18}
	
slave4OutputCurrentMaxNineteen OBJECT-TYPE
    SYNTAX      DisplayString
    MAX-ACCESS  read-write
    STATUS      current
    DESCRIPTION
	"The second output Max. current alarm value of slave4"
    ::= { slave4OutputCurrentMax 19}
	
slave4OutputCurrentMaxtwenty OBJECT-TYPE
    SYNTAX      DisplayString
    MAX-ACCESS  read-write
    STATUS      current
    DESCRIPTION
	"The second output Max. current alarm value of slave4"
    ::= { slave4OutputCurrentMax 20}
	
slave4OutputCurrentMaxTwentyone OBJECT-TYPE
    SYNTAX      DisplayString
    MAX-ACCESS  read-write
    STATUS      current
    DESCRIPTION
	"The second output Max. current alarm value of slave4"
    ::= { slave4OutputCurrentMax 21}
	
slave4OutputCurrentMaxTwentyonetwo OBJECT-TYPE
    SYNTAX      DisplayString
    MAX-ACCESS  read-write
    STATUS      current
    DESCRIPTION
	"The second output Max. current alarm value of slave4"
    ::= { slave4OutputCurrentMax 22}
	
slave4OutputCurrentMaxTwentythree OBJECT-TYPE
    SYNTAX      DisplayString
    MAX-ACCESS  read-write
    STATUS      current
    DESCRIPTION
	"The second output Max. current alarm value of slave4"
    ::= { slave4OutputCurrentMax 23}
	
slave4OutputCurrentMaxTwentyfour OBJECT-TYPE
    SYNTAX      DisplayString
    MAX-ACCESS  read-write
    STATUS      current
    DESCRIPTION
	"The second output Max. current alarm value of slave4"
    ::= { slave4OutputCurrentMax 24}
	
slave4OutputCurrentMaxTwentyfive OBJECT-TYPE
    SYNTAX      DisplayString
    MAX-ACCESS  read-write
    STATUS      current
    DESCRIPTION
	"The second output Max. current alarm value of slave4"
    ::= { slave4OutputCurrentMax 25}
	
slave4OutputCurrentMaxTwentysix OBJECT-TYPE
    SYNTAX      DisplayString
    MAX-ACCESS  read-write
    STATUS      current
    DESCRIPTION
	"The second output Max. current alarm value of slave4"
    ::= { slave4OutputCurrentMax 26}
	
slave4OutputCurrentMaxTwentyseven OBJECT-TYPE
    SYNTAX      DisplayString
    MAX-ACCESS  read-write
    STATUS      current
    DESCRIPTION
	"The second output Max. current alarm value of slave4"
    ::= { slave4OutputCurrentMax 27}
	
slave4OutputCurrentMaxTwentyeight OBJECT-TYPE
    SYNTAX      DisplayString
    MAX-ACCESS  read-write
    STATUS      current
    DESCRIPTION
	"The second output Max. current alarm value of slave4"
    ::= { slave4OutputCurrentMax 28}	
slave4OutputCurrentMaxTwentynine OBJECT-TYPE
    SYNTAX      DisplayString
    MAX-ACCESS  read-write
    STATUS      current
    DESCRIPTION
	"The second output Max. current alarm value of slave4"
    ::= { slave4OutputCurrentMax 29}
	
slave4OutputCurrentMaxThirty OBJECT-TYPE
    SYNTAX      DisplayString
    MAX-ACCESS  read-write
    STATUS      current
    DESCRIPTION
	"The second output Max. current alarm value of slave4"
    ::= { slave4OutputCurrentMax 30}
	
slave4OutputCurrentMaxThirtyone OBJECT-TYPE
    SYNTAX      DisplayString
    MAX-ACCESS  read-write
    STATUS      current
    DESCRIPTION
	"The second output Max. current alarm value of slave4"
    ::= { slave4OutputCurrentMax 31}
	
slave4OutputCurrentMaxThirtytwo OBJECT-TYPE
    SYNTAX      DisplayString
    MAX-ACCESS  read-write
    STATUS      current
    DESCRIPTION
	"The second output Max. current alarm value of slave4"
    ::= { slave4OutputCurrentMax 32}
	
slave4OutputCurrentMaxThirtythree OBJECT-TYPE
    SYNTAX      DisplayString
    MAX-ACCESS  read-write
    STATUS      current
    DESCRIPTION
	"The second output Max. current alarm value of slave4"
    ::= { slave4OutputCurrentMax 33}
	
slave4OutputCurrentMaxThirtyfour OBJECT-TYPE
    SYNTAX      DisplayString
    MAX-ACCESS  read-write
    STATUS      current
    DESCRIPTION
	"The second output Max. current alarm value of slave4"
    ::= { slave4OutputCurrentMax 34}
	
slave4OutputCurrentMaxThirtyfive OBJECT-TYPE
    SYNTAX      DisplayString
    MAX-ACCESS  read-write
    STATUS      current
    DESCRIPTION
	"The second output Max. current alarm value of slave4"
    ::= { slave4OutputCurrentMax 35}
	
slave4OutputCurrentMaxThirtysix OBJECT-TYPE
    SYNTAX      DisplayString
    MAX-ACCESS  read-write
    STATUS      current
    DESCRIPTION
	"The second output Max. current alarm value of slave4"
    ::= { slave4OutputCurrentMax 36}
	
slave4OutputCurrentMaxThirtyseven OBJECT-TYPE
    SYNTAX      DisplayString
    MAX-ACCESS  read-write
    STATUS      current
    DESCRIPTION
	"The second output Max. current alarm value of slave4"
    ::= { slave4OutputCurrentMax 37}
	
slave4OutputCurrentMaxThirtyeight OBJECT-TYPE
    SYNTAX      DisplayString
    MAX-ACCESS  read-write
    STATUS      current
    DESCRIPTION
	"The second output Max. current alarm value of slave4"
    ::= { slave4OutputCurrentMax 38}
	
slave4OutputCurrentMaxThirtynine OBJECT-TYPE
    SYNTAX      DisplayString
    MAX-ACCESS  read-write
    STATUS      current
    DESCRIPTION
	"The second output Max. current alarm value of slave4"
    ::= { slave4OutputCurrentMax 39}
	
slave4OutputCurrentMaxFourty OBJECT-TYPE
    SYNTAX      DisplayString
    MAX-ACCESS  read-write
    STATUS      current
    DESCRIPTION
	"The second output Max. current alarm value of slave4"
    ::= { slave4OutputCurrentMax 40}
	
slave4OutputCurrentMaxFourtyone OBJECT-TYPE
    SYNTAX      DisplayString
    MAX-ACCESS  read-write
    STATUS      current
    DESCRIPTION
	"The second output Max. current alarm value of slave4"
    ::= { slave4OutputCurrentMax 41}
	
slave4OutputCurrentMaxFourtytwo OBJECT-TYPE
    SYNTAX      DisplayString
    MAX-ACCESS  read-write
    STATUS      current
    DESCRIPTION
	"The second output Max. current alarm value of slave4"
    ::= { slave4OutputCurrentMax 42}
	
	
-------------------------------slave4 output powerfactor------------------------	
slave4OutputPowerfactor OBJECT IDENTIFIER ::= { slave4 9}	

slave4OutputPowerfactorOne OBJECT-TYPE
    SYNTAX      DisplayString
    MAX-ACCESS  read-only
    STATUS      current
    DESCRIPTION
	"The ouput power factor of slave4." 
	::= { slave4OutputPowerfactor 1}

slave4OutputPowerfactorTwo OBJECT-TYPE
    SYNTAX      DisplayString
    MAX-ACCESS  read-only
    STATUS      current
    DESCRIPTION
	"The ouput power factor of slave4." 
	::= { slave4OutputPowerfactor 2}
	
slave4OutputPowerfactorThree OBJECT-TYPE
    SYNTAX      DisplayString
    MAX-ACCESS  read-only
    STATUS      current
    DESCRIPTION
	"The ouput power factor of slave4." 
	::= { slave4OutputPowerfactor 3}
	
slave4OutputPowerfactorFour OBJECT-TYPE
    SYNTAX      DisplayString
    MAX-ACCESS  read-only
    STATUS      current
    DESCRIPTION
	"The ouput power factor of slave4." 
	::= { slave4OutputPowerfactor 4}
		
slave4OutputPowerfactorFive OBJECT-TYPE
    SYNTAX      DisplayString
    MAX-ACCESS  read-only
    STATUS      current
    DESCRIPTION
	"The ouput power factor of slave4." 
	::= { slave4OutputPowerfactor 5}
	
slave4OutputPowerfactorSix OBJECT-TYPE
    SYNTAX      DisplayString
    MAX-ACCESS  read-only
    STATUS      current
    DESCRIPTION
	"The ouput power factor of slave4." 
	::= { slave4OutputPowerfactor 6}
	
slave4OutputPowerfactorSeven OBJECT-TYPE
    SYNTAX      DisplayString
    MAX-ACCESS  read-only
    STATUS      current
    DESCRIPTION
	"The ouput power factor of slave4." 
	::= { slave4OutputPowerfactor 7}	
	
slave4OutputPowerfactorEight OBJECT-TYPE
    SYNTAX      DisplayString
    MAX-ACCESS  read-only
    STATUS      current
    DESCRIPTION
	"The ouput power factor of slave4." 
	::= { slave4OutputPowerfactor 8}
	
slave4OutputPowerfactorNine OBJECT-TYPE
    SYNTAX      DisplayString
    MAX-ACCESS  read-only
    STATUS      current
    DESCRIPTION
	"The ouput power factor of slave4." 
	::= { slave4OutputPowerfactor 9}
		
slave4OutputPowerfactorTen OBJECT-TYPE
    SYNTAX      DisplayString
    MAX-ACCESS  read-only
    STATUS      current
    DESCRIPTION
	"The ouput power factor of slave4." 
	::= { slave4OutputPowerfactor 10}
		
slave4OutputPowerfactorEleven OBJECT-TYPE
    SYNTAX      DisplayString
    MAX-ACCESS  read-only
    STATUS      current
    DESCRIPTION
	"The ouput power factor of slave4." 
	::= { slave4OutputPowerfactor 11}
		
slave4OutputPowerfactorTwel OBJECT-TYPE
    SYNTAX      DisplayString
    MAX-ACCESS  read-only
    STATUS      current
    DESCRIPTION
	"The ouput power factor of slave4." 
	::= { slave4OutputPowerfactor 12}
		
slave4OutputPowerfactorThirteen OBJECT-TYPE
    SYNTAX      DisplayString
    MAX-ACCESS  read-only
    STATUS      current
    DESCRIPTION
	"The ouput power factor of slave4." 
	::= { slave4OutputPowerfactor 13}
		
slave4OutputPowerfactorFourteen OBJECT-TYPE
    SYNTAX      DisplayString
    MAX-ACCESS  read-only
    STATUS      current
    DESCRIPTION
	"The ouput power factor of slave4." 
	::= { slave4OutputPowerfactor 14}
		
slave4OutputPowerfactorFifteen OBJECT-TYPE
    SYNTAX      DisplayString
    MAX-ACCESS  read-only
    STATUS      current
    DESCRIPTION
	"The ouput power factor of slave4." 
	::= { slave4OutputPowerfactor 15}
		
slave4OutputPowerfactorSixteen OBJECT-TYPE
    SYNTAX      DisplayString
    MAX-ACCESS  read-only
    STATUS      current
    DESCRIPTION
	"The ouput power factor of slave4." 
	::= { slave4OutputPowerfactor 16}
		
slave4OutputPowerfactorSeventeen OBJECT-TYPE
    SYNTAX      DisplayString
    MAX-ACCESS  read-only
    STATUS      current
    DESCRIPTION
	"The ouput power factor of slave4." 
	::= { slave4OutputPowerfactor 17}
		
slave4OutputPowerfactorEighteen OBJECT-TYPE
    SYNTAX      DisplayString
    MAX-ACCESS  read-only
    STATUS      current
    DESCRIPTION
	"The ouput power factor of slave4." 
	::= { slave4OutputPowerfactor 18}
		
slave4OutputPowerfactorNineteen OBJECT-TYPE
    SYNTAX      DisplayString
    MAX-ACCESS  read-only
    STATUS      current
    DESCRIPTION
	"The ouput power factor of slave4." 
	::= { slave4OutputPowerfactor 19}
		
slave4OutputPowerfactorTwenty OBJECT-TYPE
    SYNTAX      DisplayString
    MAX-ACCESS  read-only
    STATUS      current
    DESCRIPTION
	"The ouput power factor of slave4." 
	::= { slave4OutputPowerfactor 20}
		
slave4OutputPowerfactorTwentyone OBJECT-TYPE
    SYNTAX      DisplayString
    MAX-ACCESS  read-only
    STATUS      current
    DESCRIPTION
	"The ouput power factor of slave4." 
	::= { slave4OutputPowerfactor 21}
		
slave4OutputPowerfactorTwentytwo OBJECT-TYPE
    SYNTAX      DisplayString
    MAX-ACCESS  read-only
    STATUS      current
    DESCRIPTION
	"The ouput power factor of slave4." 
	::= { slave4OutputPowerfactor 22}
		
slave4OutputPowerfactorTwentythree OBJECT-TYPE
    SYNTAX      DisplayString
    MAX-ACCESS  read-only
    STATUS      current
    DESCRIPTION
	"The ouput power factor of slave4." 
	::= { slave4OutputPowerfactor 23}
		
slave4OutputPowerfactorTwentyfour OBJECT-TYPE
    SYNTAX      DisplayString
    MAX-ACCESS  read-only
    STATUS      current
    DESCRIPTION
	"The ouput power factor of slave4." 
	::= { slave4OutputPowerfactor 24}
		
slave4OutputPowerfactorTwentyfive OBJECT-TYPE
    SYNTAX      DisplayString
    MAX-ACCESS  read-only
    STATUS      current
    DESCRIPTION
	"The ouput power factor of slave4." 
	::= { slave4OutputPowerfactor 25}
		
slave4OutputPowerfactorTwentysix OBJECT-TYPE
    SYNTAX      DisplayString
    MAX-ACCESS  read-only
    STATUS      current
    DESCRIPTION
	"The ouput power factor of slave4." 
	::= { slave4OutputPowerfactor 26}
		
slave4OutputPowerfactorTwentyseven OBJECT-TYPE
    SYNTAX      DisplayString
    MAX-ACCESS  read-only
    STATUS      current
    DESCRIPTION
	"The ouput power factor of slave4." 
	::= { slave4OutputPowerfactor 27}
		
slave4OutputPowerfactorTwentyeight OBJECT-TYPE
    SYNTAX      DisplayString
    MAX-ACCESS  read-only
    STATUS      current
    DESCRIPTION
	"The ouput power factor of slave4." 
	::= { slave4OutputPowerfactor 28}
		
slave4OutputPowerfactorTwentynine OBJECT-TYPE
    SYNTAX      DisplayString
    MAX-ACCESS  read-only
    STATUS      current
    DESCRIPTION
	"The ouput power factor of slave4." 
	::= { slave4OutputPowerfactor 29}
		
slave4OutputPowerfactorThirty OBJECT-TYPE
    SYNTAX      DisplayString
    MAX-ACCESS  read-only
    STATUS      current
    DESCRIPTION
	"The ouput power factor of slave4." 
	::= { slave4OutputPowerfactor 30}
		
slave4OutputPowerfactorThirtyone OBJECT-TYPE
    SYNTAX      DisplayString
    MAX-ACCESS  read-only
    STATUS      current
    DESCRIPTION
	"The ouput power factor of slave4." 
	::= { slave4OutputPowerfactor 31}
		
slave4OutputPowerfactorThirtytwo OBJECT-TYPE
    SYNTAX      DisplayString
    MAX-ACCESS  read-only
    STATUS      current
    DESCRIPTION
	"The ouput power factor of slave4." 
	::= { slave4OutputPowerfactor 32}
		
slave4OutputPowerfactorThirtythree OBJECT-TYPE
    SYNTAX      DisplayString
    MAX-ACCESS  read-only
    STATUS      current
    DESCRIPTION
	"The ouput power factor of slave4." 
	::= { slave4OutputPowerfactor 33}	
	
slave4OutputPowerfactorThirtyfour OBJECT-TYPE
    SYNTAX      DisplayString
    MAX-ACCESS  read-only
    STATUS      current
    DESCRIPTION
	"The ouput power factor of slave4." 
	::= { slave4OutputPowerfactor 34}
	
	
slave4OutputPowerfactorThirtyfive OBJECT-TYPE
    SYNTAX      DisplayString
    MAX-ACCESS  read-only
    STATUS      current
    DESCRIPTION
	"The ouput power factor of slave4." 
	::= { slave4OutputPowerfactor 35}
		
slave4OutputPowerfactorThirtysix OBJECT-TYPE
    SYNTAX      DisplayString
    MAX-ACCESS  read-only
    STATUS      current
    DESCRIPTION
	"The ouput power factor of slave4." 
	::= { slave4OutputPowerfactor 36}
		
slave4OutputPowerfactorThirtyseven OBJECT-TYPE
    SYNTAX      DisplayString
    MAX-ACCESS  read-only
    STATUS      current
    DESCRIPTION
	"The ouput power factor of slave4." 
	::= { slave4OutputPowerfactor 37}
		
slave4OutputPowerfactorThirtyeight OBJECT-TYPE
    SYNTAX      DisplayString
    MAX-ACCESS  read-only
    STATUS      current
    DESCRIPTION
	"The ouput power factor of slave4." 
	::= { slave4OutputPowerfactor 38}
		
slave4OutputPowerfactorThirtynine OBJECT-TYPE
    SYNTAX      DisplayString
    MAX-ACCESS  read-only
    STATUS      current
    DESCRIPTION
	"The ouput power factor of slave4." 
	::= { slave4OutputPowerfactor 39}
		
slave4OutputPowerfactorFourty OBJECT-TYPE
    SYNTAX      DisplayString
    MAX-ACCESS  read-only
    STATUS      current
    DESCRIPTION
	"The ouput power factor of slave4." 
	::= { slave4OutputPowerfactor 40}
		
slave4OutputPowerfactorFourtyone OBJECT-TYPE
    SYNTAX      DisplayString
    MAX-ACCESS  read-only
    STATUS      current
    DESCRIPTION
	"The ouput power factor of slave4." 
	::= { slave4OutputPowerfactor 41}
		
slave4OutputPowerfactorFourtytwo OBJECT-TYPE
    SYNTAX      DisplayString
    MAX-ACCESS  read-only
    STATUS      current
    DESCRIPTION
	"The ouput power factor of slave4." 
	::= { slave4OutputPowerfactor 42}	
	
-------------------------------slave4 output energy------------------------	
slave4OutputEnergy OBJECT IDENTIFIER ::= { slave4 10}

slave4OutputEnergyOne OBJECT-TYPE
    SYNTAX      DisplayString
    MAX-ACCESS  read-only
    STATUS      current
    DESCRIPTION
	"The ouput power of slave4." 
	::= { slave4OutputEnergy 1}

slave4OutputEnergyTwo OBJECT-TYPE
    SYNTAX      DisplayString
    MAX-ACCESS  read-only
    STATUS      current
    DESCRIPTION
	"The ouput power of slave4." 
	::= { slave4OutputEnergy 2}
	
slave4OutputEnergyThree OBJECT-TYPE
    SYNTAX      DisplayString
    MAX-ACCESS  read-only
    STATUS      current
    DESCRIPTION
	"The ouput power of slave4." 
	::= { slave4OutputEnergy 3}
	
slave4OutputEnergyFour OBJECT-TYPE
    SYNTAX      DisplayString
    MAX-ACCESS  read-only
    STATUS      current
    DESCRIPTION
	"The ouput power of slave4." 
	::= { slave4OutputEnergy 4}
		
slave4OutputEnergyFive OBJECT-TYPE
    SYNTAX      DisplayString
    MAX-ACCESS  read-only
    STATUS      current
    DESCRIPTION
	"The ouput power of slave4." 
	::= { slave4OutputEnergy 5}
	
slave4OutputEnergySix OBJECT-TYPE
    SYNTAX      DisplayString
    MAX-ACCESS  read-only
    STATUS      current
    DESCRIPTION
	"The ouput power of slave4." 
	::= { slave4OutputEnergy 6}
	
slave4OutputEnergySeven OBJECT-TYPE
    SYNTAX      DisplayString
    MAX-ACCESS  read-only
    STATUS      current
    DESCRIPTION
	"The ouput power of slave4." 
	::= { slave4OutputEnergy 7}	
	
slave4OutputEnergyEight OBJECT-TYPE
    SYNTAX      DisplayString
    MAX-ACCESS  read-only
    STATUS      current
    DESCRIPTION
	"The ouput power of slave4." 
	::= { slave4OutputEnergy 8}
	
slave4OutputEnergyNine OBJECT-TYPE
    SYNTAX      DisplayString
    MAX-ACCESS  read-only
    STATUS      current
    DESCRIPTION
	"The ouput power of slave4." 
	::= { slave4OutputEnergy 9}
		
slave4OutputEnergyTen OBJECT-TYPE
    SYNTAX      DisplayString
    MAX-ACCESS  read-only
    STATUS      current
    DESCRIPTION
	"The ouput power of slave4." 
	::= { slave4OutputEnergy 10}
		
slave4OutputEnergyEleven OBJECT-TYPE
    SYNTAX      DisplayString
    MAX-ACCESS  read-only
    STATUS      current
    DESCRIPTION
	"The ouput power of slave4." 
	::= { slave4OutputEnergy 11}
		
slave4OutputEnergyTwel OBJECT-TYPE
    SYNTAX      DisplayString
    MAX-ACCESS  read-only
    STATUS      current
    DESCRIPTION
	"The ouput power of slave4." 
	::= { slave4OutputEnergy 12}
		
slave4OutputEnergyThirteen OBJECT-TYPE
    SYNTAX      DisplayString
    MAX-ACCESS  read-only
    STATUS      current
    DESCRIPTION
	"The ouput power of slave4." 
	::= { slave4OutputEnergy 13}
		
slave4OutputEnergyFourteen OBJECT-TYPE
    SYNTAX      DisplayString
    MAX-ACCESS  read-only
    STATUS      current
    DESCRIPTION
	"The ouput power of slave4." 
	::= { slave4OutputEnergy 14}
		
slave4OutputEnergyFifteen OBJECT-TYPE
    SYNTAX      DisplayString
    MAX-ACCESS  read-only
    STATUS      current
    DESCRIPTION
	"The ouput power of slave4." 
	::= { slave4OutputEnergy 15}
		
slave4OutputEnergySixteen OBJECT-TYPE
    SYNTAX      DisplayString
    MAX-ACCESS  read-only
    STATUS      current
    DESCRIPTION
	"The ouput power of slave4." 
	::= { slave4OutputEnergy 16}
		
slave4OutputEnergySeventeen OBJECT-TYPE
    SYNTAX      DisplayString
    MAX-ACCESS  read-only
    STATUS      current
    DESCRIPTION
	"The ouput power of slave4." 
	::= { slave4OutputEnergy 17}
		
slave4OutputEnergyEighteen OBJECT-TYPE
    SYNTAX      DisplayString
    MAX-ACCESS  read-only
    STATUS      current
    DESCRIPTION
	"The ouput power of slave4." 
	::= { slave4OutputEnergy 18}
		
slave4OutputEnergyNineteen OBJECT-TYPE
    SYNTAX      DisplayString
    MAX-ACCESS  read-only
    STATUS      current
    DESCRIPTION
	"The ouput power of slave4." 
	::= { slave4OutputEnergy 19}
		
slave4OutputEnergyTwenty OBJECT-TYPE
    SYNTAX      DisplayString
    MAX-ACCESS  read-only
    STATUS      current
    DESCRIPTION
	"The ouput power of slave4." 
	::= { slave4OutputEnergy 20}
		
slave4OutputEnergyTwentyone OBJECT-TYPE
    SYNTAX      DisplayString
    MAX-ACCESS  read-only
    STATUS      current
    DESCRIPTION
	"The ouput power of slave4." 
	::= { slave4OutputEnergy 21}
		
slave4OutputEnergyTwentytwo OBJECT-TYPE
    SYNTAX      DisplayString
    MAX-ACCESS  read-only
    STATUS      current
    DESCRIPTION
	"The ouput power of slave4." 
	::= { slave4OutputEnergy 22}
		
slave4OutputEnergyTwentythree OBJECT-TYPE
    SYNTAX      DisplayString
    MAX-ACCESS  read-only
    STATUS      current
    DESCRIPTION
	"The ouput power of slave4." 
	::= { slave4OutputEnergy 23}
		
slave4OutputEnergyTwentyfour OBJECT-TYPE
    SYNTAX      DisplayString
    MAX-ACCESS  read-only
    STATUS      current
    DESCRIPTION
	"The ouput power of slave4." 
	::= { slave4OutputEnergy 24}
		
slave4OutputEnergyTwentyfive OBJECT-TYPE
    SYNTAX      DisplayString
    MAX-ACCESS  read-only
    STATUS      current
    DESCRIPTION
	"The ouput power of slave4." 
	::= { slave4OutputEnergy 25}
		
slave4OutputEnergyTwentysix OBJECT-TYPE
    SYNTAX      DisplayString
    MAX-ACCESS  read-only
    STATUS      current
    DESCRIPTION
	"The ouput power of slave4." 
	::= { slave4OutputEnergy 26}
		
slave4OutputEnergyTwentyseven OBJECT-TYPE
    SYNTAX      DisplayString
    MAX-ACCESS  read-only
    STATUS      current
    DESCRIPTION
	"The ouput power of slave4." 
	::= { slave4OutputEnergy 27}
		
slave4OutputEnergyTwentyeight OBJECT-TYPE
    SYNTAX      DisplayString
    MAX-ACCESS  read-only
    STATUS      current
    DESCRIPTION
	"The ouput power of slave4." 
	::= { slave4OutputEnergy 28}
		
slave4OutputEnergyTwentynine OBJECT-TYPE
    SYNTAX      DisplayString
    MAX-ACCESS  read-only
    STATUS      current
    DESCRIPTION
	"The ouput power of slave4." 
	::= { slave4OutputEnergy 29}
		
slave4OutputEnergyThirty OBJECT-TYPE
    SYNTAX      DisplayString
    MAX-ACCESS  read-only
    STATUS      current
    DESCRIPTION
	"The ouput power of slave4." 
	::= { slave4OutputEnergy 30}
		
slave4OutputEnergyThirtyone OBJECT-TYPE
    SYNTAX      DisplayString
    MAX-ACCESS  read-only
    STATUS      current
    DESCRIPTION
	"The ouput power of slave4." 
	::= { slave4OutputEnergy 31}
		
slave4OutputEnergyThirtytwo OBJECT-TYPE
    SYNTAX      DisplayString
    MAX-ACCESS  read-only
    STATUS      current
    DESCRIPTION
	"The ouput power of slave4." 
	::= { slave4OutputEnergy 32}
		
slave4OutputEnergyThirtythree OBJECT-TYPE
    SYNTAX      DisplayString
    MAX-ACCESS  read-only
    STATUS      current
    DESCRIPTION
	"The ouput power of slave4." 
	::= { slave4OutputEnergy 33}	
	
slave4OutputEnergyThirtyfour OBJECT-TYPE
    SYNTAX      DisplayString
    MAX-ACCESS  read-only
    STATUS      current
    DESCRIPTION
	"The ouput power of slave4." 
	::= { slave4OutputEnergy 34}
	
	
slave4OutputEnergyThirtyfive OBJECT-TYPE
    SYNTAX      DisplayString
    MAX-ACCESS  read-only
    STATUS      current
    DESCRIPTION
	"The ouput power of slave4." 
	::= { slave4OutputEnergy 35}
		
slave4OutputEnergyThirtysix OBJECT-TYPE
    SYNTAX      DisplayString
    MAX-ACCESS  read-only
    STATUS      current
    DESCRIPTION
	"The ouput power of slave4." 
	::= { slave4OutputEnergy 36}
		
slave4OutputEnergyThirtyseven OBJECT-TYPE
    SYNTAX      DisplayString
    MAX-ACCESS  read-only
    STATUS      current
    DESCRIPTION
	"The ouput power of slave4." 
	::= { slave4OutputEnergy 37}
		
slave4OutputEnergyThirtyeight OBJECT-TYPE
    SYNTAX      DisplayString
    MAX-ACCESS  read-only
    STATUS      current
    DESCRIPTION
	"The ouput power of slave4." 
	::= { slave4OutputEnergy 38}
		
slave4OutputEnergyThirtynine OBJECT-TYPE
    SYNTAX      DisplayString
    MAX-ACCESS  read-only
    STATUS      current
    DESCRIPTION
	"The ouput power of slave4." 
	::= { slave4OutputEnergy 39}
		
slave4OutputEnergyFourty OBJECT-TYPE
    SYNTAX      DisplayString
    MAX-ACCESS  read-only
    STATUS      current
    DESCRIPTION
	"The ouput power of slave4." 
	::= { slave4OutputEnergy 40}
		
slave4OutputEnergyFourtyone OBJECT-TYPE
    SYNTAX      DisplayString
    MAX-ACCESS  read-only
    STATUS      current
    DESCRIPTION
	"The ouput power of slave4." 
	::= { slave4OutputEnergy 41}
		
slave4OutputEnergyFourtytwo OBJECT-TYPE
    SYNTAX      DisplayString
    MAX-ACCESS  read-only
    STATUS      current
    DESCRIPTION
	"The ouput power of slave4." 
	::= { slave4OutputEnergy 42}	
	



-------------------------------slave5 information--------------------
slave5 OBJECT IDENTIFIER ::= { pdu 6}
slave5Information OBJECT IDENTIFIER ::= { slave5 1}
slave5Name OBJECT-TYPE
    SYNTAX      DisplayString
    MAX-ACCESS  read-write
    STATUS      current
    DESCRIPTION
	"This is the first device."
    ::= { slave5Information 1}
    
slave5Type OBJECT-TYPE
    SYNTAX      DisplayString
    MAX-ACCESS  read-only
    STATUS      current
    DESCRIPTION
	"This is device type "
    ::= { slave5Information 2}
    
slave5OutputNumber OBJECT-TYPE 
    SYNTAX      Integer32
    MAX-ACCESS  read-only
    STATUS      current
    DESCRIPTION
	"This is the number of output bits"
	::= { slave5Information 3}
	
slave5MacAdress OBJECT-TYPE
    SYNTAX      DisplayString
    MAX-ACCESS  read-only
    STATUS      current
    DESCRIPTION
	"This is device MAC adress"
    ::= { slave5Information 4}	

slave5Vison OBJECT-TYPE
    SYNTAX      DisplayString
    MAX-ACCESS  read-only
    STATUS      current
    DESCRIPTION
	"This is device vison "
    ::= { slave5Information 5}

slave5Frequency OBJECT-TYPE
    SYNTAX      Integer32
    MAX-ACCESS  read-only
    STATUS      current
    DESCRIPTION
	"This is device frequency "
    ::= { slave5Information 6}
	
slave5Emission OBJECT-TYPE
    SYNTAX      DisplayString
    MAX-ACCESS  read-only
    STATUS      current
    DESCRIPTION
	"This is device emission "
    ::= { slave5Information 7}	
	
slave5RunTime OBJECT-TYPE
    SYNTAX      DisplayString
    MAX-ACCESS  read-only
    STATUS      current
    DESCRIPTION
	"This is device running time "
    ::= { slave5Information 8}	

slave5BuzzerSwitch OBJECT-TYPE
    SYNTAX      DisplayString
    MAX-ACCESS  read-write
    STATUS      current
    DESCRIPTION
	"This is device buzzer switch."
    ::= { slave5Information 9}	

	
-------------------------------slave5 phase--------------------
slave5Phase OBJECT IDENTIFIER ::= { slave5 2}	
	
slave5PhaseOne OBJECT IDENTIFIER ::= { slave5Phase 1}	    
slave5PhaseOneCurrent OBJECT-TYPE
    SYNTAX      DisplayString
    MAX-ACCESS  read-only
    STATUS      current
    DESCRIPTION
	"The power of phase one"
    ::= { slave5PhaseOne 1}

slave5PhaseOneVoltage OBJECT-TYPE
    SYNTAX      DisplayString
    MAX-ACCESS  read-only
    STATUS      current
    DESCRIPTION
	"The power of phase one"
    ::= { slave5PhaseOne 2}

slave5PhaseOnePower OBJECT-TYPE
    SYNTAX      DisplayString
    MAX-ACCESS  read-only
    STATUS      current
    DESCRIPTION
	"The power of phase one"
    ::= { slave5PhaseOne 3}
	
slave5PhaseOnePowerfactor OBJECT-TYPE
    SYNTAX      DisplayString
    MAX-ACCESS  read-only
    STATUS      current
    DESCRIPTION
	"The power of phase one"
    ::= { slave5PhaseOne 4}	
	
slave5PhaseOneEnergy OBJECT-TYPE
    SYNTAX      DisplayString
    MAX-ACCESS  read-only
    STATUS      current
    DESCRIPTION
	"The power of phase one"
    ::= { slave5PhaseOne 5}	
		
slave5PhaseOneCurrentMin OBJECT-TYPE
    SYNTAX      DisplayString
    MAX-ACCESS  read-write
    STATUS      current
    DESCRIPTION
	"The power of phase one"
    ::= { slave5PhaseOne 6}	
	
slave5PhaseOneCurrentMinCritical OBJECT-TYPE
    SYNTAX      DisplayString
    MAX-ACCESS  read-write
    STATUS      current
    DESCRIPTION
	"The power of phase one"
    ::= { slave5PhaseOne 7}
	
slave5PhaseOneCurrentMaxCritical OBJECT-TYPE
    SYNTAX      DisplayString
    MAX-ACCESS  read-write
    STATUS      current
    DESCRIPTION
	"The power of phase one"
    ::= { slave5PhaseOne 8}
	
slave5PhaseOneCurrentMax OBJECT-TYPE
    SYNTAX      DisplayString
    MAX-ACCESS  read-write
    STATUS      current
    DESCRIPTION
	"The power of phase one"
    ::= { slave5PhaseOne 9}
	
slave5PhaseOneVoltageMin OBJECT-TYPE
    SYNTAX      DisplayString
    MAX-ACCESS  read-write
    STATUS      current
    DESCRIPTION
	"The power of phase one"
    ::= { slave5PhaseOne 10}
	
slave5PhaseOneVoltageMinCritical OBJECT-TYPE
    SYNTAX      DisplayString
    MAX-ACCESS  read-write
    STATUS      current
    DESCRIPTION
	"The power of phase one"
    ::= { slave5PhaseOne 11}

slave5PhaseOneVoltageMaxCritical OBJECT-TYPE
    SYNTAX      DisplayString
    MAX-ACCESS  read-write
    STATUS      current
    DESCRIPTION
	"The power of phase one"
    ::= { slave5PhaseOne 12}
	
slave5PhaseOneVoltageMax OBJECT-TYPE
    SYNTAX      DisplayString
    MAX-ACCESS  read-write
    STATUS      current
    DESCRIPTION
	"The power of phase one"
    ::= { slave5PhaseOne 13}


slave5PhaseTwo OBJECT IDENTIFIER ::= { slave5Phase 2}	    
slave5PhaseTwoCurrent OBJECT-TYPE
    SYNTAX      DisplayString
    MAX-ACCESS  read-only
    STATUS      current
    DESCRIPTION
	"The power of phase one"
    ::= { slave5PhaseTwo 1}

slave5PhaseTwoVoltage OBJECT-TYPE
    SYNTAX      DisplayString
    MAX-ACCESS  read-only
    STATUS      current
    DESCRIPTION
	"The power of phase one"
    ::= { slave5PhaseTwo 2}

slave5PhaseTwoPower OBJECT-TYPE
    SYNTAX      DisplayString
    MAX-ACCESS  read-only
    STATUS      current
    DESCRIPTION
	"The power of phase one"
    ::= { slave5PhaseTwo 3}
	
slave5PhaseTwoPowerfactor OBJECT-TYPE
    SYNTAX      DisplayString
    MAX-ACCESS  read-only
    STATUS      current
    DESCRIPTION
	"The power of phase one"
    ::= { slave5PhaseTwo 4}	
	
slave5PhaseTwoEnergy OBJECT-TYPE
    SYNTAX      DisplayString
    MAX-ACCESS  read-only
    STATUS      current
    DESCRIPTION
	"The power of phase one"
    ::= { slave5PhaseTwo 5}	
		
slave5PhaseTwoCurrentMin OBJECT-TYPE
    SYNTAX      DisplayString
    MAX-ACCESS  read-write
    STATUS      current
    DESCRIPTION
	"The power of phase one"
    ::= { slave5PhaseTwo 6}	
	
slave5PhaseTwoCurrentMinCritical OBJECT-TYPE
    SYNTAX      DisplayString
    MAX-ACCESS  read-write
    STATUS      current
    DESCRIPTION
	"The power of phase one"
    ::= { slave5PhaseTwo 7}
	
slave5PhaseTwoCurrentMaxCritical OBJECT-TYPE
    SYNTAX      DisplayString
    MAX-ACCESS  read-write
    STATUS      current
    DESCRIPTION
	"The power of phase one"
    ::= { slave5PhaseTwo 8}
	
slave5PhaseTwoCurrentMax OBJECT-TYPE
    SYNTAX      DisplayString
    MAX-ACCESS  read-write
    STATUS      current
    DESCRIPTION
	"The power of phase one"
    ::= { slave5PhaseTwo 9}
	
slave5PhaseTwoVoltageMin OBJECT-TYPE
    SYNTAX      DisplayString
    MAX-ACCESS  read-write
    STATUS      current
    DESCRIPTION
	"The power of phase one"
    ::= { slave5PhaseTwo 10}
	
slave5PhaseTwoVoltageMinCritical OBJECT-TYPE
    SYNTAX      DisplayString
    MAX-ACCESS  read-write
    STATUS      current
    DESCRIPTION
	"The power of phase one"
    ::= { slave5PhaseTwo 11}

slave5PhaseTwoVoltageMaxCritical OBJECT-TYPE
    SYNTAX      DisplayString
    MAX-ACCESS  read-write
    STATUS      current
    DESCRIPTION
	"The power of phase one"
    ::= { slave5PhaseTwo 12}
	
slave5PhaseTwoVoltageMax OBJECT-TYPE
    SYNTAX      DisplayString
    MAX-ACCESS  read-write
    STATUS      current
    DESCRIPTION
	"The power of phase one"
    ::= { slave5PhaseTwo 13}
	
	
slave5PhaseThree OBJECT IDENTIFIER ::= { slave5Phase 3}	    
slave5PhaseThreeCurrent OBJECT-TYPE
    SYNTAX      DisplayString
    MAX-ACCESS  read-only
    STATUS      current
    DESCRIPTION
	"The power of phase one"
    ::= { slave5PhaseThree 1}

slave5PhaseThreeVoltage OBJECT-TYPE
    SYNTAX      DisplayString
    MAX-ACCESS  read-only
    STATUS      current
    DESCRIPTION
	"The power of phase one"
    ::= { slave5PhaseThree 2}

slave5PhaseThreePower OBJECT-TYPE
    SYNTAX      DisplayString
    MAX-ACCESS  read-only
    STATUS      current
    DESCRIPTION
	"The power of phase one"
    ::= { slave5PhaseThree 3}
	
slave5PhaseThreePowerfactor OBJECT-TYPE
    SYNTAX      DisplayString
    MAX-ACCESS  read-only
    STATUS      current
    DESCRIPTION
	"The power of phase one"
    ::= { slave5PhaseThree 4}	
	
slave5PhaseThreeEnergy OBJECT-TYPE
    SYNTAX      DisplayString
    MAX-ACCESS  read-only
    STATUS      current
    DESCRIPTION
	"The power of phase one"
    ::= { slave5PhaseThree 5}	
		
slave5PhaseThreeCurrentMin OBJECT-TYPE
    SYNTAX      DisplayString
    MAX-ACCESS  read-write
    STATUS      current
    DESCRIPTION
	"The power of phase one"
    ::= { slave5PhaseThree 6}	
	
slave5PhaseThreeCurrentMinCritical OBJECT-TYPE
    SYNTAX      DisplayString
    MAX-ACCESS  read-write
    STATUS      current
    DESCRIPTION
	"The power of phase one"
    ::= { slave5PhaseThree 7}
	
slave5PhaseThreeCurrentMaxCritical OBJECT-TYPE
    SYNTAX      DisplayString
    MAX-ACCESS  read-write
    STATUS      current
    DESCRIPTION
	"The power of phase one"
    ::= { slave5PhaseThree 8}
	
slave5PhaseThreeCurrentMax OBJECT-TYPE
    SYNTAX      DisplayString
    MAX-ACCESS  read-write
    STATUS      current
    DESCRIPTION
	"The power of phase one"
    ::= { slave5PhaseThree 9}
	
slave5PhaseThreeVoltageMin OBJECT-TYPE
    SYNTAX      DisplayString
    MAX-ACCESS  read-write
    STATUS      current
    DESCRIPTION
	"The power of phase one"
    ::= { slave5PhaseThree 10}
	
slave5PhaseThreeVoltageMinCritical OBJECT-TYPE
    SYNTAX      DisplayString
    MAX-ACCESS  read-write
    STATUS      current
    DESCRIPTION
	"The power of phase one"
    ::= { slave5PhaseThree 11}

slave5PhaseThreeVoltageMaxCritical OBJECT-TYPE
    SYNTAX      DisplayString
    MAX-ACCESS  read-write
    STATUS      current
    DESCRIPTION
	"The power of phase one"
    ::= { slave5PhaseThree 12}
	
slave5PhaseThreeVoltageMax OBJECT-TYPE
    SYNTAX      DisplayString
    MAX-ACCESS  read-write
    STATUS      current
    DESCRIPTION
	"The power of phase one"
    ::= { slave5PhaseThree 13}
	
	
-------------------------------slave5 circuit--------------------	
slave5Circuit OBJECT IDENTIFIER ::= { slave5 3}	

slave5CircuitOne OBJECT IDENTIFIER ::= { slave5Circuit 1}	    
slave5CircuitOneBreaker OBJECT-TYPE
    SYNTAX      DisplayString
    MAX-ACCESS  read-only
    STATUS      current
    DESCRIPTION
	"The power of phase one"
    ::= { slave5CircuitOne 1}
	
slave5CircuitOneManagementBit OBJECT-TYPE
    SYNTAX      DisplayString
    MAX-ACCESS  read-only
    STATUS      current
    DESCRIPTION
	"The power of phase one"
    ::= { slave5CircuitOne 2}	

slave5CircuitOneCurrent OBJECT-TYPE
    SYNTAX      DisplayString
    MAX-ACCESS  read-only
    STATUS      current
    DESCRIPTION
	"The power of phase one"
    ::= { slave5CircuitOne 3}

slave5CircuitOneVoltage OBJECT-TYPE
    SYNTAX      DisplayString
    MAX-ACCESS  read-only
    STATUS      current
    DESCRIPTION
	"The power of phase one"
    ::= { slave5CircuitOne 4}

slave5CircuitOneEnergy OBJECT-TYPE
    SYNTAX      DisplayString
    MAX-ACCESS  read-only
    STATUS      current
    DESCRIPTION
	"The power of phase one"
    ::= { slave5CircuitOne 5}	
	
slave5CircuitOnePower OBJECT-TYPE
    SYNTAX      DisplayString
    MAX-ACCESS  read-only
    STATUS      current
    DESCRIPTION
	"The power of phase one"
    ::= { slave5CircuitOne 6}
	
slave5CircuitOneCurrentMin OBJECT-TYPE
    SYNTAX      DisplayString
    MAX-ACCESS  read-write
    STATUS      current
    DESCRIPTION
	"The power of phase one"
    ::= { slave5CircuitOne 7}	
	
slave5CircuitOneCurrentMinCritical OBJECT-TYPE
    SYNTAX      DisplayString
    MAX-ACCESS  read-write
    STATUS      current
    DESCRIPTION
	"The power of phase one"
    ::= { slave5CircuitOne 8}
	
slave5CircuitOneCurrentMaxCritical OBJECT-TYPE
    SYNTAX      DisplayString
    MAX-ACCESS  read-write
    STATUS      current
    DESCRIPTION
	"The power of phase one"
    ::= { slave5CircuitOne 9}
	
slave5CircuitOneCurrentMax OBJECT-TYPE
    SYNTAX      DisplayString
    MAX-ACCESS  read-write
    STATUS      current
    DESCRIPTION
	"The power of phase one"
    ::= { slave5CircuitOne 10}
	

slave5CircuitTwo OBJECT IDENTIFIER ::= { slave5Circuit 2}	    
slave5CircuitTwoBreaker OBJECT-TYPE
    SYNTAX      DisplayString
    MAX-ACCESS  read-only
    STATUS      current
    DESCRIPTION
	"The power of phase one"
    ::= { slave5CircuitTwo 1}
	
slave5CircuitTwoManagementBit OBJECT-TYPE
    SYNTAX      DisplayString
    MAX-ACCESS  read-only
    STATUS      current
    DESCRIPTION
	"The power of phase one"
    ::= { slave5CircuitTwo 2}	

slave5CircuitTwoCurrent OBJECT-TYPE
    SYNTAX      DisplayString
    MAX-ACCESS  read-only
    STATUS      current
    DESCRIPTION
	"The power of phase one"
    ::= { slave5CircuitTwo 3}

slave5CircuitTwoVoltage OBJECT-TYPE
    SYNTAX      DisplayString
    MAX-ACCESS  read-only
    STATUS      current
    DESCRIPTION
	"The power of phase one"
    ::= { slave5CircuitTwo 4}

slave5CircuitTwoEnergy OBJECT-TYPE
    SYNTAX      DisplayString
    MAX-ACCESS  read-only
    STATUS      current
    DESCRIPTION
	"The power of phase one"
    ::= { slave5CircuitTwo 5}	
	
slave5CircuitTwoPower OBJECT-TYPE
    SYNTAX      DisplayString
    MAX-ACCESS  read-only
    STATUS      current
    DESCRIPTION
	"The power of phase one"
    ::= { slave5CircuitTwo 6}
	
slave5CircuitTwoCurrentMin OBJECT-TYPE
    SYNTAX      DisplayString
    MAX-ACCESS  read-write
    STATUS      current
    DESCRIPTION
	"The power of phase one"
    ::= { slave5CircuitTwo 7}	
	
slave5CircuitTwoCurrentMinCritical OBJECT-TYPE
    SYNTAX      DisplayString
    MAX-ACCESS  read-write
    STATUS      current
    DESCRIPTION
	"The power of phase one"
    ::= { slave5CircuitTwo 8}
	
slave5CircuitTwoCurrentMaxCritical OBJECT-TYPE
    SYNTAX      DisplayString
    MAX-ACCESS  read-write
    STATUS      current
    DESCRIPTION
	"The power of phase one"
    ::= { slave5CircuitTwo 9}
	
slave5CircuitTwoCurrentMax OBJECT-TYPE
    SYNTAX      DisplayString
    MAX-ACCESS  read-write
    STATUS      current
    DESCRIPTION
	"The power of phase one"
    ::= { slave5CircuitTwo 10}
	
	
slave5CircuitThree OBJECT IDENTIFIER ::= { slave5Circuit 3}	    
slave5CircuitThreeBreaker OBJECT-TYPE
    SYNTAX      DisplayString
    MAX-ACCESS  read-only
    STATUS      current
    DESCRIPTION
	"The power of phase one"
    ::= { slave5CircuitThree 1}
	
slave5CircuitThreeManagementBit OBJECT-TYPE
    SYNTAX      DisplayString
    MAX-ACCESS  read-only
    STATUS      current
    DESCRIPTION
	"The power of phase one"
    ::= { slave5CircuitThree 2}	

slave5CircuitThreeCurrent OBJECT-TYPE
    SYNTAX      DisplayString
    MAX-ACCESS  read-only
    STATUS      current
    DESCRIPTION
	"The power of phase one"
    ::= { slave5CircuitThree 3}

slave5CircuitThreeVoltage OBJECT-TYPE
    SYNTAX      DisplayString
    MAX-ACCESS  read-only
    STATUS      current
    DESCRIPTION
	"The power of phase one"
    ::= { slave5CircuitThree 4}

slave5CircuitThreeEnergy OBJECT-TYPE
    SYNTAX      DisplayString
    MAX-ACCESS  read-only
    STATUS      current
    DESCRIPTION
	"The power of phase one"
    ::= { slave5CircuitThree 5}	
	
slave5CircuitThreePower OBJECT-TYPE
    SYNTAX      DisplayString
    MAX-ACCESS  read-only
    STATUS      current
    DESCRIPTION
	"The power of phase one"
    ::= { slave5CircuitThree 6}
	
slave5CircuitThreeCurrentMin OBJECT-TYPE
    SYNTAX      DisplayString
    MAX-ACCESS  read-write
    STATUS      current
    DESCRIPTION
	"The power of phase one"
    ::= { slave5CircuitThree 7}	
	
slave5CircuitThreeCurrentMinCritical OBJECT-TYPE
    SYNTAX      DisplayString
    MAX-ACCESS  read-write
    STATUS      current
    DESCRIPTION
	"The power of phase one"
    ::= { slave5CircuitThree 8}
	
slave5CircuitThreeCurrentMaxCritical OBJECT-TYPE
    SYNTAX      DisplayString
    MAX-ACCESS  read-write
    STATUS      current
    DESCRIPTION
	"The power of phase one"
    ::= { slave5CircuitThree 9}
	
slave5CircuitThreeCurrentMax OBJECT-TYPE
    SYNTAX      DisplayString
    MAX-ACCESS  read-write
    STATUS      current
    DESCRIPTION
	"The power of phase one"
    ::= { slave5CircuitThree 10}
	
	
slave5CircuitFour OBJECT IDENTIFIER ::= { slave5Circuit 4}	    
slave5CircuitFourBreaker OBJECT-TYPE
    SYNTAX      DisplayString
    MAX-ACCESS  read-only
    STATUS      current
    DESCRIPTION
	"The power of phase one"
    ::= { slave5CircuitFour 1}
	
slave5CircuitFourManagementBit OBJECT-TYPE
    SYNTAX      DisplayString
    MAX-ACCESS  read-only
    STATUS      current
    DESCRIPTION
	"The power of phase one"
    ::= { slave5CircuitFour 2}	

slave5CircuitFourCurrent OBJECT-TYPE
    SYNTAX      DisplayString
    MAX-ACCESS  read-only
    STATUS      current
    DESCRIPTION
	"The power of phase one"
    ::= { slave5CircuitFour 3}

slave5CircuitFourVoltage OBJECT-TYPE
    SYNTAX      DisplayString
    MAX-ACCESS  read-only
    STATUS      current
    DESCRIPTION
	"The power of phase one"
    ::= { slave5CircuitFour 4}

slave5CircuitFourEnergy OBJECT-TYPE
    SYNTAX      DisplayString
    MAX-ACCESS  read-only
    STATUS      current
    DESCRIPTION
	"The power of phase one"
    ::= { slave5CircuitFour 5}	
	
slave5CircuitFourPower OBJECT-TYPE
    SYNTAX      DisplayString
    MAX-ACCESS  read-only
    STATUS      current
    DESCRIPTION
	"The power of phase one"
    ::= { slave5CircuitFour 6}
	
slave5CircuitFourCurrentMin OBJECT-TYPE
    SYNTAX      DisplayString
    MAX-ACCESS  read-write
    STATUS      current
    DESCRIPTION
	"The power of phase one"
    ::= { slave5CircuitFour 7}	
	
slave5CircuitFourCurrentMinCritical OBJECT-TYPE
    SYNTAX      DisplayString
    MAX-ACCESS  read-write
    STATUS      current
    DESCRIPTION
	"The power of phase one"
    ::= { slave5CircuitFour 8}
	
slave5CircuitFourCurrentMaxCritical OBJECT-TYPE
    SYNTAX      DisplayString
    MAX-ACCESS  read-write
    STATUS      current
    DESCRIPTION
	"The power of phase one"
    ::= { slave5CircuitFour 9}
	
slave5CircuitFourCurrentMax OBJECT-TYPE
    SYNTAX      DisplayString
    MAX-ACCESS  read-write
    STATUS      current
    DESCRIPTION
	"The power of phase one"
    ::= { slave5CircuitFour 10}
	
	
slave5CircuitFive OBJECT IDENTIFIER ::= { slave5Circuit 5}	    
slave5CircuitFiveBreaker OBJECT-TYPE
    SYNTAX      DisplayString
    MAX-ACCESS  read-only
    STATUS      current
    DESCRIPTION
	"The power of phase one"
    ::= { slave5CircuitFive 1}
	
slave5CircuitFiveManagementBit OBJECT-TYPE
    SYNTAX      DisplayString
    MAX-ACCESS  read-only
    STATUS      current
    DESCRIPTION
	"The power of phase one"
    ::= { slave5CircuitFive 2}	

slave5CircuitFiveCurrent OBJECT-TYPE
    SYNTAX      DisplayString
    MAX-ACCESS  read-only
    STATUS      current
    DESCRIPTION
	"The power of phase one"
    ::= { slave5CircuitFive 3}

slave5CircuitFiveVoltage OBJECT-TYPE
    SYNTAX      DisplayString
    MAX-ACCESS  read-only
    STATUS      current
    DESCRIPTION
	"The power of phase one"
    ::= { slave5CircuitFive 4}

slave5CircuitFiveEnergy OBJECT-TYPE
    SYNTAX      DisplayString
    MAX-ACCESS  read-only
    STATUS      current
    DESCRIPTION
	"The power of phase one"
    ::= { slave5CircuitFive 5}	
	
slave5CircuitFivePower OBJECT-TYPE
    SYNTAX      DisplayString
    MAX-ACCESS  read-only
    STATUS      current
    DESCRIPTION
	"The power of phase one"
    ::= { slave5CircuitFive 6}
		
slave5CircuitFiveCurrentMin OBJECT-TYPE
    SYNTAX      DisplayString
    MAX-ACCESS  read-write
    STATUS      current
    DESCRIPTION
	"The power of phase one"
    ::= { slave5CircuitFive 7}	
	
slave5CircuitFiveCurrentMinCritical OBJECT-TYPE
    SYNTAX      DisplayString
    MAX-ACCESS  read-write
    STATUS      current
    DESCRIPTION
	"The power of phase one"
    ::= { slave5CircuitFive 8}
	
slave5CircuitFiveCurrentMaxCritical OBJECT-TYPE
    SYNTAX      DisplayString
    MAX-ACCESS  read-write
    STATUS      current
    DESCRIPTION
	"The power of phase one"
    ::= { slave5CircuitFive 9}
	
slave5CircuitFiveCurrentMax OBJECT-TYPE
    SYNTAX      DisplayString
    MAX-ACCESS  read-write
    STATUS      current
    DESCRIPTION
	"The power of phase one"
    ::= { slave5CircuitFive 10}

	
slave5CircuitSix OBJECT IDENTIFIER ::= { slave5Circuit 6}	    
slave5CircuitSixBreaker OBJECT-TYPE
    SYNTAX      DisplayString
    MAX-ACCESS  read-only
    STATUS      current
    DESCRIPTION
	"The power of phase one"
    ::= { slave5CircuitSix 1}
	
slave5CircuitSixManagementBit OBJECT-TYPE
    SYNTAX      DisplayString
    MAX-ACCESS  read-only
    STATUS      current
    DESCRIPTION
	"The power of phase one"
    ::= { slave5CircuitSix 2}	

slave5CircuitSixCurrent OBJECT-TYPE
    SYNTAX      DisplayString
    MAX-ACCESS  read-only
    STATUS      current
    DESCRIPTION
	"The power of phase one"
    ::= { slave5CircuitSix 3}

slave5CircuitSixVoltage OBJECT-TYPE
    SYNTAX      DisplayString
    MAX-ACCESS  read-only
    STATUS      current
    DESCRIPTION
	"The power of phase one"
    ::= { slave5CircuitSix 4}

slave5CircuitSixEnergy OBJECT-TYPE
    SYNTAX      DisplayString
    MAX-ACCESS  read-only
    STATUS      current
    DESCRIPTION
	"The power of phase one"
    ::= { slave5CircuitSix 5}	
	
slave5CircuitSixPower OBJECT-TYPE
    SYNTAX      DisplayString
    MAX-ACCESS  read-only
    STATUS      current
    DESCRIPTION
	"The power of phase one"
    ::= { slave5CircuitSix 6}
	
slave5CircuitSixCurrentMin OBJECT-TYPE
    SYNTAX      DisplayString
    MAX-ACCESS  read-write
    STATUS      current
    DESCRIPTION
	"The power of phase one"
    ::= { slave5CircuitSix 7}	
	
slave5CircuitSixCurrentMinCritical OBJECT-TYPE
    SYNTAX      DisplayString
    MAX-ACCESS  read-write
    STATUS      current
    DESCRIPTION
	"The power of phase one"
    ::= { slave5CircuitSix 8}
	
slave5CircuitSixCurrentMaxCritical OBJECT-TYPE
    SYNTAX      DisplayString
    MAX-ACCESS  read-write
    STATUS      current
    DESCRIPTION
	"The power of phase one"
    ::= { slave5CircuitSix 9}
	
slave5CircuitSixCurrentMax OBJECT-TYPE
    SYNTAX      DisplayString
    MAX-ACCESS  read-write
    STATUS      current
    DESCRIPTION
	"The power of phase one"
    ::= { slave5CircuitSix 10}

	
-------------------------------slave5 sensor------------------------	
slave5Sensor OBJECT IDENTIFIER ::= { slave5 4}
slave5SensorTemperatureOne OBJECT-TYPE
    SYNTAX      DisplayString
    MAX-ACCESS  read-only
    STATUS      current
    DESCRIPTION
	"This is the first device."
    ::= { slave5Sensor 1}
	
slave5SensorTemperatureTwo OBJECT-TYPE
    SYNTAX      DisplayString
    MAX-ACCESS  read-only
    STATUS      current
    DESCRIPTION
	"This is the first device."
    ::= { slave5Sensor 2}

slave5SensorHumidityOne OBJECT-TYPE
    SYNTAX      DisplayString
    MAX-ACCESS  read-only
    STATUS      current
    DESCRIPTION
	"This is the first device."
    ::= { slave5Sensor 3}

slave5SensorHumidityTwo OBJECT-TYPE
    SYNTAX      DisplayString
    MAX-ACCESS  read-only
    STATUS      current
    DESCRIPTION
	"This is the first device."
    ::= { slave5Sensor 4}	

slave5SensorDoorOne OBJECT-TYPE
    SYNTAX      DisplayString
    MAX-ACCESS  read-only
    STATUS      current
    DESCRIPTION
	"This is the first device."
    ::= { slave5Sensor 5}

slave5SensorDoorTwo OBJECT-TYPE
    SYNTAX      DisplayString
    MAX-ACCESS  read-only
    STATUS      current
    DESCRIPTION
	"This is the first device."
    ::= { slave5Sensor 6}	
	
slave5SensorSmoke OBJECT-TYPE
    SYNTAX      DisplayString
    MAX-ACCESS  read-only
    STATUS      current
    DESCRIPTION
	"This is the first device."
    ::= { slave5Sensor 7}
	
slave5SensorWater OBJECT-TYPE
    SYNTAX      DisplayString
    MAX-ACCESS  read-only
    STATUS      current
    DESCRIPTION
	"This is the first device."
    ::= { slave5Sensor 8}
	
slave5SensorTemperatureOneMin OBJECT-TYPE
    SYNTAX      DisplayString
    MAX-ACCESS  read-write
    STATUS      current
    DESCRIPTION
	"This is the first device."
    ::= { slave5Sensor 9}
	
slave5SensorTemperatureOneMinCritical OBJECT-TYPE
    SYNTAX      DisplayString
    MAX-ACCESS  read-write
    STATUS      current
    DESCRIPTION
	"This is the first device."
    ::= { slave5Sensor 10}	
	
slave5SensorTemperatureOneMaxCritical OBJECT-TYPE
    SYNTAX      DisplayString
    MAX-ACCESS  read-write
    STATUS      current
    DESCRIPTION
	"This is the first device."
    ::= { slave5Sensor 11}
	
slave5SensorTemperatureOneMax OBJECT-TYPE
    SYNTAX      DisplayString
    MAX-ACCESS  read-write
    STATUS      current
    DESCRIPTION
	"This is the first device."
    ::= { slave5Sensor 12}

slave5SensorTemperatureTwoMin OBJECT-TYPE
    SYNTAX      DisplayString
    MAX-ACCESS  read-write
    STATUS      current
    DESCRIPTION
	"This is the first device."
    ::= { slave5Sensor 13}
	
slave5SensorTemperatureTwoMinCritical OBJECT-TYPE
    SYNTAX      DisplayString
    MAX-ACCESS  read-write
    STATUS      current
    DESCRIPTION
	"This is the first device."
    ::= { slave5Sensor 14}	
	
slave5SensorTemperatureTwoMaxCritical OBJECT-TYPE
    SYNTAX      DisplayString
    MAX-ACCESS  read-write
    STATUS      current
    DESCRIPTION
	"This is the first device."
    ::= { slave5Sensor 15}
	
slave5SensorTemperatureTwoMax OBJECT-TYPE
    SYNTAX      DisplayString
    MAX-ACCESS  read-write
    STATUS      current
    DESCRIPTION
	"This is the first device."
    ::= { slave5Sensor 16}
	
slave5SensorHumidityOneMin OBJECT-TYPE
    SYNTAX      DisplayString
    MAX-ACCESS  read-write
    STATUS      current
    DESCRIPTION
	"This is the first device."
    ::= { slave5Sensor 17}
	
slave5SensorHumidityOneMinCritical OBJECT-TYPE
    SYNTAX      DisplayString
    MAX-ACCESS  read-write
    STATUS      current
    DESCRIPTION
	"This is the first device."
    ::= { slave5Sensor 18}	
	
slave5SensorHumidityOneMaxCritical OBJECT-TYPE
    SYNTAX      DisplayString
    MAX-ACCESS  read-write
    STATUS      current
    DESCRIPTION
	"This is the first device."
    ::= { slave5Sensor 19}
	
slave5SensorHumidityOneMax OBJECT-TYPE
    SYNTAX      DisplayString
    MAX-ACCESS  read-write
    STATUS      current
    DESCRIPTION
	"This is the first device."
    ::= { slave5Sensor 20}

slave5SensorHumidityTwoMin OBJECT-TYPE
    SYNTAX      DisplayString
    MAX-ACCESS  read-write
    STATUS      current
    DESCRIPTION
	"This is the first device."
    ::= { slave5Sensor 21}
	
slave5SensorHumidityTwoMinCritical OBJECT-TYPE
    SYNTAX      DisplayString
    MAX-ACCESS  read-write
    STATUS      current
    DESCRIPTION
	"This is the first device."
    ::= { slave5Sensor 22}	
	
slave5SensorHumidityTwoMaxCritical OBJECT-TYPE
    SYNTAX      DisplayString
    MAX-ACCESS  read-write
    STATUS      current
    DESCRIPTION
	"This is the first device."
    ::= { slave5Sensor 23}
	
slave5SensorHumidityTwoMax OBJECT-TYPE
    SYNTAX      DisplayString
    MAX-ACCESS  read-write
    STATUS      current
    DESCRIPTION
	"This is the first device."
    ::= { slave5Sensor 24}
	
-------------------------------slave5 output name------------------------	
slave5OutputName OBJECT IDENTIFIER ::= { slave5 5}
slave5OutputNameOne OBJECT-TYPE
    SYNTAX      DisplayString
    MAX-ACCESS  read-write
    STATUS      current
    DESCRIPTION
	"The first output name of slave5"
    ::= { slave5OutputName 1}

slave5OutputNameTwo OBJECT-TYPE
    SYNTAX      DisplayString
    MAX-ACCESS  read-write
    STATUS      current
    DESCRIPTION
	"The second output name of slave5"
    ::= { slave5OutputName 2}

slave5OutputNameThree OBJECT-TYPE
    SYNTAX      DisplayString
    MAX-ACCESS  read-write
    STATUS      current
    DESCRIPTION
	"The second output name of slave5"
    ::= { slave5OutputName 3}

slave5OutputNameFour OBJECT-TYPE
    SYNTAX      DisplayString
    MAX-ACCESS  read-write
    STATUS      current
    DESCRIPTION
	"The second output name of slave5"
    ::= { slave5OutputName 4}

slave5OutputNameFive OBJECT-TYPE
    SYNTAX      DisplayString
    MAX-ACCESS  read-write
    STATUS      current
    DESCRIPTION
	"The second output name of slave5"
    ::= { slave5OutputName 5}

slave5OutputNameSix OBJECT-TYPE
    SYNTAX      DisplayString
    MAX-ACCESS  read-write
    STATUS      current
    DESCRIPTION
	"The second output name of slave5"
    ::= { slave5OutputName 6}

slave5OutputNameSeven OBJECT-TYPE
    SYNTAX      DisplayString
    MAX-ACCESS  read-write
    STATUS      current
    DESCRIPTION
	"The second output name of slave5"
    ::= { slave5OutputName 7}

slave5OutputNameEight OBJECT-TYPE
    SYNTAX      DisplayString
    MAX-ACCESS  read-write
    STATUS      current
    DESCRIPTION
	"The second output name of slave5"
    ::= { slave5OutputName 8}

slave5OutputNameNine OBJECT-TYPE
    SYNTAX      DisplayString
    MAX-ACCESS  read-write
    STATUS      current
    DESCRIPTION
	"The second output name of slave5"
    ::= { slave5OutputName 9}

slave5OutputNameTen OBJECT-TYPE
    SYNTAX      DisplayString
    MAX-ACCESS  read-write
    STATUS      current
    DESCRIPTION
	"The second output name of slave5"
    ::= { slave5OutputName 10}

slave5OutputNameEleven OBJECT-TYPE
    SYNTAX      DisplayString
    MAX-ACCESS  read-write
    STATUS      current
    DESCRIPTION
	"The second output name of slave5"
    ::= { slave5OutputName 11}

slave5OutputNameTwel OBJECT-TYPE
    SYNTAX      DisplayString
    MAX-ACCESS  read-write
    STATUS      current
    DESCRIPTION
	"The second output name of slave5"
    ::= { slave5OutputName 12}

slave5OutputNameThirteen OBJECT-TYPE
    SYNTAX      DisplayString
    MAX-ACCESS  read-write
    STATUS      current
    DESCRIPTION
	"The second output name of slave5"
    ::= { slave5OutputName 13}

slave5OutputNameFourteen OBJECT-TYPE
    SYNTAX      DisplayString
    MAX-ACCESS  read-write
    STATUS      current
    DESCRIPTION
	"The second output name of slave5"
    ::= { slave5OutputName 14}

slave5OutputNameFifteen OBJECT-TYPE
    SYNTAX      DisplayString
    MAX-ACCESS  read-write
    STATUS      current
    DESCRIPTION
	"The second output name of slave5"
    ::= { slave5OutputName 15}

slave5OutputNameSixteen OBJECT-TYPE
    SYNTAX      DisplayString
    MAX-ACCESS  read-write
    STATUS      current
    DESCRIPTION
	"The second output name of slave5"
    ::= { slave5OutputName 16}

slave5OutputNameSeventeen OBJECT-TYPE
    SYNTAX      DisplayString
    MAX-ACCESS  read-write
    STATUS      current
    DESCRIPTION
	"The second output name of slave5"
    ::= { slave5OutputName 17}

slave5OutputNameEighteen OBJECT-TYPE
    SYNTAX      DisplayString
    MAX-ACCESS  read-write
    STATUS      current
    DESCRIPTION
	"The second output name of slave5"
    ::= { slave5OutputName 18}
	
slave5OutputNameNineteen OBJECT-TYPE
    SYNTAX      DisplayString
    MAX-ACCESS  read-write
    STATUS      current
    DESCRIPTION
	"The second output name of slave5"
    ::= { slave5OutputName 19}
	
slave5OutputNametwenty OBJECT-TYPE
    SYNTAX      DisplayString
    MAX-ACCESS  read-write
    STATUS      current
    DESCRIPTION
	"The second output name of slave5"
    ::= { slave5OutputName 20}
	
slave5OutputNameTwentyone OBJECT-TYPE
    SYNTAX      DisplayString
    MAX-ACCESS  read-write
    STATUS      current
    DESCRIPTION
	"The second output name of slave5"
    ::= { slave5OutputName 21}
	
slave5OutputNameTwentyonetwo OBJECT-TYPE
    SYNTAX      DisplayString
    MAX-ACCESS  read-write
    STATUS      current
    DESCRIPTION
	"The second output name of slave5"
    ::= { slave5OutputName 22}
	
slave5OutputNameTwentythree OBJECT-TYPE
    SYNTAX      DisplayString
    MAX-ACCESS  read-write
    STATUS      current
    DESCRIPTION
	"The second output name of slave5"
    ::= { slave5OutputName 23}
	
slave5OutputNameTwentyfour OBJECT-TYPE
    SYNTAX      DisplayString
    MAX-ACCESS  read-write
    STATUS      current
    DESCRIPTION
	"The second output name of slave5"
    ::= { slave5OutputName 24}
	
slave5OutputNameTwentyfive OBJECT-TYPE
    SYNTAX      DisplayString
    MAX-ACCESS  read-write
    STATUS      current
    DESCRIPTION
	"The second output name of slave5"
    ::= { slave5OutputName 25}
	
slave5OutputNameTwentysix OBJECT-TYPE
    SYNTAX      DisplayString
    MAX-ACCESS  read-write
    STATUS      current
    DESCRIPTION
	"The second output name of slave5"
    ::= { slave5OutputName 26}
	
slave5OutputNameTwentyseven OBJECT-TYPE
    SYNTAX      DisplayString
    MAX-ACCESS  read-write
    STATUS      current
    DESCRIPTION
	"The second output name of slave5"
    ::= { slave5OutputName 27}
	
slave5OutputNameTwentyeight OBJECT-TYPE
    SYNTAX      DisplayString
    MAX-ACCESS  read-write
    STATUS      current
    DESCRIPTION
	"The second output name of slave5"
    ::= { slave5OutputName 28}	
slave5OutputNameTwentynine OBJECT-TYPE
    SYNTAX      DisplayString
    MAX-ACCESS  read-write
    STATUS      current
    DESCRIPTION
	"The second output name of slave5"
    ::= { slave5OutputName 29}
	
slave5OutputNameThirty OBJECT-TYPE
    SYNTAX      DisplayString
    MAX-ACCESS  read-write
    STATUS      current
    DESCRIPTION
	"The second output name of slave5"
    ::= { slave5OutputName 30}
	
slave5OutputNameThirtyone OBJECT-TYPE
    SYNTAX      DisplayString
    MAX-ACCESS  read-write
    STATUS      current
    DESCRIPTION
	"The second output name of slave5"
    ::= { slave5OutputName 31}
	
slave5OutputNameThirtytwo OBJECT-TYPE
    SYNTAX      DisplayString
    MAX-ACCESS  read-write
    STATUS      current
    DESCRIPTION
	"The second output name of slave5"
    ::= { slave5OutputName 32}
	
slave5OutputNameThirtythree OBJECT-TYPE
    SYNTAX      DisplayString
    MAX-ACCESS  read-write
    STATUS      current
    DESCRIPTION
	"The second output name of slave5"
    ::= { slave5OutputName 33}
	
slave5OutputNameThirtyfour OBJECT-TYPE
    SYNTAX      DisplayString
    MAX-ACCESS  read-write
    STATUS      current
    DESCRIPTION
	"The second output name of slave5"
    ::= { slave5OutputName 34}
	
slave5OutputNameThirtyfive OBJECT-TYPE
    SYNTAX      DisplayString
    MAX-ACCESS  read-write
    STATUS      current
    DESCRIPTION
	"The second output name of slave5"
    ::= { slave5OutputName 35}
	
slave5OutputNameThirtysix OBJECT-TYPE
    SYNTAX      DisplayString
    MAX-ACCESS  read-write
    STATUS      current
    DESCRIPTION
	"The second output name of slave5"
    ::= { slave5OutputName 36}
	
slave5OutputNameThirtyseven OBJECT-TYPE
    SYNTAX      DisplayString
    MAX-ACCESS  read-write
    STATUS      current
    DESCRIPTION
	"The second output name of slave5"
    ::= { slave5OutputName 37}
	
slave5OutputNameThirtyeight OBJECT-TYPE
    SYNTAX      DisplayString
    MAX-ACCESS  read-write
    STATUS      current
    DESCRIPTION
	"The second output name of slave5"
    ::= { slave5OutputName 38}
	
slave5OutputNameThirtynine OBJECT-TYPE
    SYNTAX      DisplayString
    MAX-ACCESS  read-write
    STATUS      current
    DESCRIPTION
	"The second output name of slave5"
    ::= { slave5OutputName 39}
	
slave5OutputNameFourty OBJECT-TYPE
    SYNTAX      DisplayString
    MAX-ACCESS  read-write
    STATUS      current
    DESCRIPTION
	"The second output name of slave5"
    ::= { slave5OutputName 40}
	
slave5OutputNameFourtyone OBJECT-TYPE
    SYNTAX      DisplayString
    MAX-ACCESS  read-write
    STATUS      current
    DESCRIPTION
	"The second output name of slave5"
    ::= { slave5OutputName 41}
	
slave5OutputNameFourtytwo OBJECT-TYPE
    SYNTAX      DisplayString
    MAX-ACCESS  read-write
    STATUS      current
    DESCRIPTION
	"The second output name of slave5"
    ::= { slave5OutputName 42}	

	
-------------------------------slave5 output delay------------------------	
slave5OutputDelay OBJECT IDENTIFIER ::= { slave5 6}	
slave5OutputDelayOne OBJECT-TYPE
    SYNTAX      DisplayString
    MAX-ACCESS  read-write
    STATUS      current
    DESCRIPTION
	"The first output name of slave5"
    ::= { slave5OutputDelay 1}

slave5OutputDelayTwo OBJECT-TYPE
    SYNTAX      DisplayString
    MAX-ACCESS  read-write
    STATUS      current
    DESCRIPTION
	"The second output name of slave5"
    ::= { slave5OutputDelay 2}

slave5OutputDelayThree OBJECT-TYPE
    SYNTAX      DisplayString
    MAX-ACCESS  read-write
    STATUS      current
    DESCRIPTION
	"The second output name of slave5"
    ::= { slave5OutputDelay 3}

slave5OutputDelayFour OBJECT-TYPE
    SYNTAX      DisplayString
    MAX-ACCESS  read-write
    STATUS      current
    DESCRIPTION
	"The second output name of slave5"
    ::= { slave5OutputDelay 4}

slave5OutputDelayFive OBJECT-TYPE
    SYNTAX      DisplayString
    MAX-ACCESS  read-write
    STATUS      current
    DESCRIPTION
	"The second output name of slave5"
    ::= { slave5OutputDelay 5}

slave5OutputDelaySix OBJECT-TYPE
    SYNTAX      DisplayString
    MAX-ACCESS  read-write
    STATUS      current
    DESCRIPTION
	"The second output name of slave5"
    ::= { slave5OutputDelay 6}

slave5OutputDelaySeven OBJECT-TYPE
    SYNTAX      DisplayString
    MAX-ACCESS  read-write
    STATUS      current
    DESCRIPTION
	"The second output name of slave5"
    ::= { slave5OutputDelay 7}

slave5OutputDelayEight OBJECT-TYPE
    SYNTAX      DisplayString
    MAX-ACCESS  read-write
    STATUS      current
    DESCRIPTION
	"The second output name of slave5"
    ::= { slave5OutputDelay 8}

slave5OutputDelayNine OBJECT-TYPE
    SYNTAX      DisplayString
    MAX-ACCESS  read-write
    STATUS      current
    DESCRIPTION
	"The second output name of slave5"
    ::= { slave5OutputDelay 9}

slave5OutputDelayTen OBJECT-TYPE
    SYNTAX      DisplayString
    MAX-ACCESS  read-write
    STATUS      current
    DESCRIPTION
	"The second output name of slave5"
    ::= { slave5OutputDelay 10}

slave5OutputDelayEleven OBJECT-TYPE
    SYNTAX      DisplayString
    MAX-ACCESS  read-write
    STATUS      current
    DESCRIPTION
	"The second output name of slave5"
    ::= { slave5OutputDelay 11}

slave5OutputDelayTwel OBJECT-TYPE
    SYNTAX      DisplayString
    MAX-ACCESS  read-write
    STATUS      current
    DESCRIPTION
	"The second output name of slave5"
    ::= { slave5OutputDelay 12}

slave5OutputDelayThirteen OBJECT-TYPE
    SYNTAX      DisplayString
    MAX-ACCESS  read-write
    STATUS      current
    DESCRIPTION
	"The second output name of slave5"
    ::= { slave5OutputDelay 13}

slave5OutputDelayFourteen OBJECT-TYPE
    SYNTAX      DisplayString
    MAX-ACCESS  read-write
    STATUS      current
    DESCRIPTION
	"The second output name of slave5"
    ::= { slave5OutputDelay 14}

slave5OutputDelayFifteen OBJECT-TYPE
    SYNTAX      DisplayString
    MAX-ACCESS  read-write
    STATUS      current
    DESCRIPTION
	"The second output name of slave5"
    ::= { slave5OutputDelay 15}

slave5OutputDelaySixteen OBJECT-TYPE
    SYNTAX      DisplayString
    MAX-ACCESS  read-write
    STATUS      current
    DESCRIPTION
	"The second output name of slave5"
    ::= { slave5OutputDelay 16}

slave5OutputDelaySeventeen OBJECT-TYPE
    SYNTAX      DisplayString
    MAX-ACCESS  read-write
    STATUS      current
    DESCRIPTION
	"The second output name of slave5"
    ::= { slave5OutputDelay 17}

slave5OutputDelayEighteen OBJECT-TYPE
    SYNTAX      DisplayString
    MAX-ACCESS  read-write
    STATUS      current
    DESCRIPTION
	"The second output name of slave5"
    ::= { slave5OutputDelay 18}
	
slave5OutputDelayNineteen OBJECT-TYPE
    SYNTAX      DisplayString
    MAX-ACCESS  read-write
    STATUS      current
    DESCRIPTION
	"The second output name of slave5"
    ::= { slave5OutputDelay 19}
	
slave5OutputDelaytwenty OBJECT-TYPE
    SYNTAX      DisplayString
    MAX-ACCESS  read-write
    STATUS      current
    DESCRIPTION
	"The second output name of slave5"
    ::= { slave5OutputDelay 20}
	
slave5OutputDelayTwentyone OBJECT-TYPE
    SYNTAX      DisplayString
    MAX-ACCESS  read-write
    STATUS      current
    DESCRIPTION
	"The second output name of slave5"
    ::= { slave5OutputDelay 21}
	
slave5OutputDelayTwentyonetwo OBJECT-TYPE
    SYNTAX      DisplayString
    MAX-ACCESS  read-write
    STATUS      current
    DESCRIPTION
	"The second output name of slave5"
    ::= { slave5OutputDelay 22}
	
slave5OutputDelayTwentythree OBJECT-TYPE
    SYNTAX      DisplayString
    MAX-ACCESS  read-write
    STATUS      current
    DESCRIPTION
	"The second output name of slave5"
    ::= { slave5OutputDelay 23}
	
slave5OutputDelayTwentyfour OBJECT-TYPE
    SYNTAX      DisplayString
    MAX-ACCESS  read-write
    STATUS      current
    DESCRIPTION
	"The second output name of slave5"
    ::= { slave5OutputDelay 24}
	
slave5OutputDelayTwentyfive OBJECT-TYPE
    SYNTAX      DisplayString
    MAX-ACCESS  read-write
    STATUS      current
    DESCRIPTION
	"The second output name of slave5"
    ::= { slave5OutputDelay 25}
	
slave5OutputDelayTwentysix OBJECT-TYPE
    SYNTAX      DisplayString
    MAX-ACCESS  read-write
    STATUS      current
    DESCRIPTION
	"The second output name of slave5"
    ::= { slave5OutputDelay 26}
	
slave5OutputDelayTwentyseven OBJECT-TYPE
    SYNTAX      DisplayString
    MAX-ACCESS  read-write
    STATUS      current
    DESCRIPTION
	"The second output name of slave5"
    ::= { slave5OutputDelay 27}
	
slave5OutputDelayTwentyeight OBJECT-TYPE
    SYNTAX      DisplayString
    MAX-ACCESS  read-write
    STATUS      current
    DESCRIPTION
	"The second output name of slave5"
    ::= { slave5OutputDelay 28}	
slave5OutputDelayTwentynine OBJECT-TYPE
    SYNTAX      DisplayString
    MAX-ACCESS  read-write
    STATUS      current
    DESCRIPTION
	"The second output name of slave5"
    ::= { slave5OutputDelay 29}
	
slave5OutputDelayThirty OBJECT-TYPE
    SYNTAX      DisplayString
    MAX-ACCESS  read-write
    STATUS      current
    DESCRIPTION
	"The second output name of slave5"
    ::= { slave5OutputDelay 30}
	
slave5OutputDelayThirtyone OBJECT-TYPE
    SYNTAX      DisplayString
    MAX-ACCESS  read-write
    STATUS      current
    DESCRIPTION
	"The second output name of slave5"
    ::= { slave5OutputDelay 31}
	
slave5OutputDelayThirtytwo OBJECT-TYPE
    SYNTAX      DisplayString
    MAX-ACCESS  read-write
    STATUS      current
    DESCRIPTION
	"The second output name of slave5"
    ::= { slave5OutputDelay 32}
	
slave5OutputDelayThirtythree OBJECT-TYPE
    SYNTAX      DisplayString
    MAX-ACCESS  read-write
    STATUS      current
    DESCRIPTION
	"The second output name of slave5"
    ::= { slave5OutputDelay 33}
	
slave5OutputDelayThirtyfour OBJECT-TYPE
    SYNTAX      DisplayString
    MAX-ACCESS  read-write
    STATUS      current
    DESCRIPTION
	"The second output name of slave5"
    ::= { slave5OutputDelay 34}
	
slave5OutputDelayThirtyfive OBJECT-TYPE
    SYNTAX      DisplayString
    MAX-ACCESS  read-write
    STATUS      current
    DESCRIPTION
	"The second output name of slave5"
    ::= { slave5OutputDelay 35}
	
slave5OutputDelayThirtysix OBJECT-TYPE
    SYNTAX      DisplayString
    MAX-ACCESS  read-write
    STATUS      current
    DESCRIPTION
	"The second output name of slave5"
    ::= { slave5OutputDelay 36}
	
slave5OutputDelayThirtyseven OBJECT-TYPE
    SYNTAX      DisplayString
    MAX-ACCESS  read-write
    STATUS      current
    DESCRIPTION
	"The second output name of slave5"
    ::= { slave5OutputDelay 37}
	
slave5OutputDelayThirtyeight OBJECT-TYPE
    SYNTAX      DisplayString
    MAX-ACCESS  read-write
    STATUS      current
    DESCRIPTION
	"The second output name of slave5"
    ::= { slave5OutputDelay 38}
	
slave5OutputDelayThirtynine OBJECT-TYPE
    SYNTAX      DisplayString
    MAX-ACCESS  read-write
    STATUS      current
    DESCRIPTION
	"The second output name of slave5"
    ::= { slave5OutputDelay 39}
	
slave5OutputDelayFourty OBJECT-TYPE
    SYNTAX      DisplayString
    MAX-ACCESS  read-write
    STATUS      current
    DESCRIPTION
	"The second output name of slave5"
    ::= { slave5OutputDelay 40}
	
slave5OutputDelayFourtyone OBJECT-TYPE
    SYNTAX      DisplayString
    MAX-ACCESS  read-write
    STATUS      current
    DESCRIPTION
	"The second output name of slave5"
    ::= { slave5OutputDelay 41}
	
slave5OutputDelayFourtytwo OBJECT-TYPE
    SYNTAX      DisplayString
    MAX-ACCESS  read-write
    STATUS      current
    DESCRIPTION
	"The second output name of slave5"
    ::= { slave5OutputDelay 42}

	
-------------------------------slave5 output switch------------------------	
slave5OutputSwitch OBJECT IDENTIFIER ::= { slave5 7}		
slave5OutputSwitchOne OBJECT-TYPE
    SYNTAX      DisplayString
    MAX-ACCESS  read-write
    STATUS      current
    DESCRIPTION
	"The first output name of slave5"
    ::= { slave5OutputSwitch 1}

slave5OutputSwitchTwo OBJECT-TYPE
    SYNTAX      DisplayString
    MAX-ACCESS  read-write
    STATUS      current
    DESCRIPTION
	"The second output name of slave5"
    ::= { slave5OutputSwitch 2}

slave5OutputSwitchThree OBJECT-TYPE
    SYNTAX      DisplayString
    MAX-ACCESS  read-write
    STATUS      current
    DESCRIPTION
	"The second output name of slave5"
    ::= { slave5OutputSwitch 3}

slave5OutputSwitchFour OBJECT-TYPE
    SYNTAX      DisplayString
    MAX-ACCESS  read-write
    STATUS      current
    DESCRIPTION
	"The second output name of slave5"
    ::= { slave5OutputSwitch 4}

slave5OutputSwitchFive OBJECT-TYPE
    SYNTAX      DisplayString
    MAX-ACCESS  read-write
    STATUS      current
    DESCRIPTION
	"The second output name of slave5"
    ::= { slave5OutputSwitch 5}

slave5OutputSwitchSix OBJECT-TYPE
    SYNTAX      DisplayString
    MAX-ACCESS  read-write
    STATUS      current
    DESCRIPTION
	"The second output name of slave5"
    ::= { slave5OutputSwitch 6}

slave5OutputSwitchSeven OBJECT-TYPE
    SYNTAX      DisplayString
    MAX-ACCESS  read-write
    STATUS      current
    DESCRIPTION
	"The second output name of slave5"
    ::= { slave5OutputSwitch 7}

slave5OutputSwitchEight OBJECT-TYPE
    SYNTAX      DisplayString
    MAX-ACCESS  read-write
    STATUS      current
    DESCRIPTION
	"The second output name of slave5"
    ::= { slave5OutputSwitch 8}

slave5OutputSwitchNine OBJECT-TYPE
    SYNTAX      DisplayString
    MAX-ACCESS  read-write
    STATUS      current
    DESCRIPTION
	"The second output name of slave5"
    ::= { slave5OutputSwitch 9}

slave5OutputSwitchTen OBJECT-TYPE
    SYNTAX      DisplayString
    MAX-ACCESS  read-write
    STATUS      current
    DESCRIPTION
	"The second output name of slave5"
    ::= { slave5OutputSwitch 10}

slave5OutputSwitchEleven OBJECT-TYPE
    SYNTAX      DisplayString
    MAX-ACCESS  read-write
    STATUS      current
    DESCRIPTION
	"The second output name of slave5"
    ::= { slave5OutputSwitch 11}

slave5OutputSwitchTwel OBJECT-TYPE
    SYNTAX      DisplayString
    MAX-ACCESS  read-write
    STATUS      current
    DESCRIPTION
	"The second output name of slave5"
    ::= { slave5OutputSwitch 12}

slave5OutputSwitchThirteen OBJECT-TYPE
    SYNTAX      DisplayString
    MAX-ACCESS  read-write
    STATUS      current
    DESCRIPTION
	"The second output name of slave5"
    ::= { slave5OutputSwitch 13}

slave5OutputSwitchFourteen OBJECT-TYPE
    SYNTAX      DisplayString
    MAX-ACCESS  read-write
    STATUS      current
    DESCRIPTION
	"The second output name of slave5"
    ::= { slave5OutputSwitch 14}

slave5OutputSwitchFifteen OBJECT-TYPE
    SYNTAX      DisplayString
    MAX-ACCESS  read-write
    STATUS      current
    DESCRIPTION
	"The second output name of slave5"
    ::= { slave5OutputSwitch 15}

slave5OutputSwitchSixteen OBJECT-TYPE
    SYNTAX      DisplayString
    MAX-ACCESS  read-write
    STATUS      current
    DESCRIPTION
	"The second output name of slave5"
    ::= { slave5OutputSwitch 16}

slave5OutputSwitchSeventeen OBJECT-TYPE
    SYNTAX      DisplayString
    MAX-ACCESS  read-write
    STATUS      current
    DESCRIPTION
	"The second output name of slave5"
    ::= { slave5OutputSwitch 17}

slave5OutputSwitchEighteen OBJECT-TYPE
    SYNTAX      DisplayString
    MAX-ACCESS  read-write
    STATUS      current
    DESCRIPTION
	"The second output name of slave5"
    ::= { slave5OutputSwitch 18}
	
slave5OutputSwitchNineteen OBJECT-TYPE
    SYNTAX      DisplayString
    MAX-ACCESS  read-write
    STATUS      current
    DESCRIPTION
	"The second output name of slave5"
    ::= { slave5OutputSwitch 19}
	
slave5OutputSwitchtwenty OBJECT-TYPE
    SYNTAX      DisplayString
    MAX-ACCESS  read-write
    STATUS      current
    DESCRIPTION
	"The second output name of slave5"
    ::= { slave5OutputSwitch 20}
	
slave5OutputSwitchTwentyone OBJECT-TYPE
    SYNTAX      DisplayString
    MAX-ACCESS  read-write
    STATUS      current
    DESCRIPTION
	"The second output name of slave5"
    ::= { slave5OutputSwitch 21}
	
slave5OutputSwitchTwentyonetwo OBJECT-TYPE
    SYNTAX      DisplayString
    MAX-ACCESS  read-write
    STATUS      current
    DESCRIPTION
	"The second output name of slave5"
    ::= { slave5OutputSwitch 22}
	
slave5OutputSwitchTwentythree OBJECT-TYPE
    SYNTAX      DisplayString
    MAX-ACCESS  read-write
    STATUS      current
    DESCRIPTION
	"The second output name of slave5"
    ::= { slave5OutputSwitch 23}
	
slave5OutputSwitchTwentyfour OBJECT-TYPE
    SYNTAX      DisplayString
    MAX-ACCESS  read-write
    STATUS      current
    DESCRIPTION
	"The second output name of slave5"
    ::= { slave5OutputSwitch 24}
	
slave5OutputSwitchTwentyfive OBJECT-TYPE
    SYNTAX      DisplayString
    MAX-ACCESS  read-write
    STATUS      current
    DESCRIPTION
	"The second output name of slave5"
    ::= { slave5OutputSwitch 25}
	
slave5OutputSwitchTwentysix OBJECT-TYPE
    SYNTAX      DisplayString
    MAX-ACCESS  read-write
    STATUS      current
    DESCRIPTION
	"The second output name of slave5"
    ::= { slave5OutputSwitch 26}
	
slave5OutputSwitchTwentyseven OBJECT-TYPE
    SYNTAX      DisplayString
    MAX-ACCESS  read-write
    STATUS      current
    DESCRIPTION
	"The second output name of slave5"
    ::= { slave5OutputSwitch 27}
	
slave5OutputSwitchTwentyeight OBJECT-TYPE
    SYNTAX      DisplayString
    MAX-ACCESS  read-write
    STATUS      current
    DESCRIPTION
	"The second output name of slave5"
    ::= { slave5OutputSwitch 28}	
slave5OutputSwitchTwentynine OBJECT-TYPE
    SYNTAX      DisplayString
    MAX-ACCESS  read-write
    STATUS      current
    DESCRIPTION
	"The second output name of slave5"
    ::= { slave5OutputSwitch 29}
	
slave5OutputSwitchThirty OBJECT-TYPE
    SYNTAX      DisplayString
    MAX-ACCESS  read-write
    STATUS      current
    DESCRIPTION
	"The second output name of slave5"
    ::= { slave5OutputSwitch 30}
	
slave5OutputSwitchThirtyone OBJECT-TYPE
    SYNTAX      DisplayString
    MAX-ACCESS  read-write
    STATUS      current
    DESCRIPTION
	"The second output name of slave5"
    ::= { slave5OutputSwitch 31}
	
slave5OutputSwitchThirtytwo OBJECT-TYPE
    SYNTAX      DisplayString
    MAX-ACCESS  read-write
    STATUS      current
    DESCRIPTION
	"The second output name of slave5"
    ::= { slave5OutputSwitch 32}
	
slave5OutputSwitchThirtythree OBJECT-TYPE
    SYNTAX      DisplayString
    MAX-ACCESS  read-write
    STATUS      current
    DESCRIPTION
	"The second output name of slave5"
    ::= { slave5OutputSwitch 33}
	
slave5OutputSwitchThirtyfour OBJECT-TYPE
    SYNTAX      DisplayString
    MAX-ACCESS  read-write
    STATUS      current
    DESCRIPTION
	"The second output name of slave5"
    ::= { slave5OutputSwitch 34}
	
slave5OutputSwitchThirtyfive OBJECT-TYPE
    SYNTAX      DisplayString
    MAX-ACCESS  read-write
    STATUS      current
    DESCRIPTION
	"The second output name of slave5"
    ::= { slave5OutputSwitch 35}
	
slave5OutputSwitchThirtysix OBJECT-TYPE
    SYNTAX      DisplayString
    MAX-ACCESS  read-write
    STATUS      current
    DESCRIPTION
	"The second output name of slave5"
    ::= { slave5OutputSwitch 36}
	
slave5OutputSwitchThirtyseven OBJECT-TYPE
    SYNTAX      DisplayString
    MAX-ACCESS  read-write
    STATUS      current
    DESCRIPTION
	"The second output name of slave5"
    ::= { slave5OutputSwitch 37}
	
slave5OutputSwitchThirtyeight OBJECT-TYPE
    SYNTAX      DisplayString
    MAX-ACCESS  read-write
    STATUS      current
    DESCRIPTION
	"The second output name of slave5"
    ::= { slave5OutputSwitch 38}
	
slave5OutputSwitchThirtynine OBJECT-TYPE
    SYNTAX      DisplayString
    MAX-ACCESS  read-write
    STATUS      current
    DESCRIPTION
	"The second output name of slave5"
    ::= { slave5OutputSwitch 39}
	
slave5OutputSwitchFourty OBJECT-TYPE
    SYNTAX      DisplayString
    MAX-ACCESS  read-write
    STATUS      current
    DESCRIPTION
	"The second output name of slave5"
    ::= { slave5OutputSwitch 40}
	
slave5OutputSwitchFourtyone OBJECT-TYPE
    SYNTAX      DisplayString
    MAX-ACCESS  read-write
    STATUS      current
    DESCRIPTION
	"The second output name of slave5"
    ::= { slave5OutputSwitch 41}
	
slave5OutputSwitchFourtytwo OBJECT-TYPE
    SYNTAX      DisplayString
    MAX-ACCESS  read-write
    STATUS      current
    DESCRIPTION
	"The second output name of slave5"
    ::= { slave5OutputSwitch 42}

	
-------------------------------slave5 output current------------------------	
slave5OutputCurrent OBJECT IDENTIFIER ::= { slave5 8}		
slave5OutputCurrentValue OBJECT IDENTIFIER ::= { slave5OutputCurrent 1}	

slave5OutputCurrentValueOne OBJECT-TYPE
    SYNTAX      DisplayString
    MAX-ACCESS  read-write
    STATUS      current
    DESCRIPTION
	"The first output name of slave5"
    ::= { slave5OutputCurrentValue 1}

slave5OutputCurrentValueTwo OBJECT-TYPE
    SYNTAX      DisplayString
    MAX-ACCESS  read-write
    STATUS      current
    DESCRIPTION
	"The second output name of slave5"
    ::= { slave5OutputCurrentValue 2}

slave5OutputCurrentValueThree OBJECT-TYPE
    SYNTAX      DisplayString
    MAX-ACCESS  read-write
    STATUS      current
    DESCRIPTION
	"The second output name of slave5"
    ::= { slave5OutputCurrentValue 3}

slave5OutputCurrentValueFour OBJECT-TYPE
    SYNTAX      DisplayString
    MAX-ACCESS  read-write
    STATUS      current
    DESCRIPTION
	"The second output name of slave5"
    ::= { slave5OutputCurrentValue 4}

slave5OutputCurrentValueFive OBJECT-TYPE
    SYNTAX      DisplayString
    MAX-ACCESS  read-write
    STATUS      current
    DESCRIPTION
	"The second output name of slave5"
    ::= { slave5OutputCurrentValue 5}

slave5OutputCurrentValueSix OBJECT-TYPE
    SYNTAX      DisplayString
    MAX-ACCESS  read-write
    STATUS      current
    DESCRIPTION
	"The second output name of slave5"
    ::= { slave5OutputCurrentValue 6}

slave5OutputCurrentValueSeven OBJECT-TYPE
    SYNTAX      DisplayString
    MAX-ACCESS  read-write
    STATUS      current
    DESCRIPTION
	"The second output name of slave5"
    ::= { slave5OutputCurrentValue 7}

slave5OutputCurrentValueEight OBJECT-TYPE
    SYNTAX      DisplayString
    MAX-ACCESS  read-write
    STATUS      current
    DESCRIPTION
	"The second output name of slave5"
    ::= { slave5OutputCurrentValue 8}

slave5OutputCurrentValueNine OBJECT-TYPE
    SYNTAX      DisplayString
    MAX-ACCESS  read-write
    STATUS      current
    DESCRIPTION
	"The second output name of slave5"
    ::= { slave5OutputCurrentValue 9}

slave5OutputCurrentValueTen OBJECT-TYPE
    SYNTAX      DisplayString
    MAX-ACCESS  read-write
    STATUS      current
    DESCRIPTION
	"The second output name of slave5"
    ::= { slave5OutputCurrentValue 10}

slave5OutputCurrentValueEleven OBJECT-TYPE
    SYNTAX      DisplayString
    MAX-ACCESS  read-write
    STATUS      current
    DESCRIPTION
	"The second output name of slave5"
    ::= { slave5OutputCurrentValue 11}

slave5OutputCurrentValueTwel OBJECT-TYPE
    SYNTAX      DisplayString
    MAX-ACCESS  read-write
    STATUS      current
    DESCRIPTION
	"The second output name of slave5"
    ::= { slave5OutputCurrentValue 12}

slave5OutputCurrentValueThirteen OBJECT-TYPE
    SYNTAX      DisplayString
    MAX-ACCESS  read-write
    STATUS      current
    DESCRIPTION
	"The second output name of slave5"
    ::= { slave5OutputCurrentValue 13}

slave5OutputCurrentValueFourteen OBJECT-TYPE
    SYNTAX      DisplayString
    MAX-ACCESS  read-write
    STATUS      current
    DESCRIPTION
	"The second output name of slave5"
    ::= { slave5OutputCurrentValue 14}

slave5OutputCurrentValueFifteen OBJECT-TYPE
    SYNTAX      DisplayString
    MAX-ACCESS  read-write
    STATUS      current
    DESCRIPTION
	"The second output name of slave5"
    ::= { slave5OutputCurrentValue 15}

slave5OutputCurrentValueSixteen OBJECT-TYPE
    SYNTAX      DisplayString
    MAX-ACCESS  read-write
    STATUS      current
    DESCRIPTION
	"The second output name of slave5"
    ::= { slave5OutputCurrentValue 16}

slave5OutputCurrentValueSeventeen OBJECT-TYPE
    SYNTAX      DisplayString
    MAX-ACCESS  read-write
    STATUS      current
    DESCRIPTION
	"The second output name of slave5"
    ::= { slave5OutputCurrentValue 17}

slave5OutputCurrentValueEighteen OBJECT-TYPE
    SYNTAX      DisplayString
    MAX-ACCESS  read-write
    STATUS      current
    DESCRIPTION
	"The second output name of slave5"
    ::= { slave5OutputCurrentValue 18}
	
slave5OutputCurrentValueNineteen OBJECT-TYPE
    SYNTAX      DisplayString
    MAX-ACCESS  read-write
    STATUS      current
    DESCRIPTION
	"The second output name of slave5"
    ::= { slave5OutputCurrentValue 19}
	
slave5OutputCurrentValuetwenty OBJECT-TYPE
    SYNTAX      DisplayString
    MAX-ACCESS  read-write
    STATUS      current
    DESCRIPTION
	"The second output name of slave5"
    ::= { slave5OutputCurrentValue 20}
	
slave5OutputCurrentValueTwentyone OBJECT-TYPE
    SYNTAX      DisplayString
    MAX-ACCESS  read-write
    STATUS      current
    DESCRIPTION
	"The second output name of slave5"
    ::= { slave5OutputCurrentValue 21}
	
slave5OutputCurrentValueTwentyonetwo OBJECT-TYPE
    SYNTAX      DisplayString
    MAX-ACCESS  read-write
    STATUS      current
    DESCRIPTION
	"The second output name of slave5"
    ::= { slave5OutputCurrentValue 22}
	
slave5OutputCurrentValueTwentythree OBJECT-TYPE
    SYNTAX      DisplayString
    MAX-ACCESS  read-write
    STATUS      current
    DESCRIPTION
	"The second output name of slave5"
    ::= { slave5OutputCurrentValue 23}
	
slave5OutputCurrentValueTwentyfour OBJECT-TYPE
    SYNTAX      DisplayString
    MAX-ACCESS  read-write
    STATUS      current
    DESCRIPTION
	"The second output name of slave5"
    ::= { slave5OutputCurrentValue 24}
	
slave5OutputCurrentValueTwentyfive OBJECT-TYPE
    SYNTAX      DisplayString
    MAX-ACCESS  read-write
    STATUS      current
    DESCRIPTION
	"The second output name of slave5"
    ::= { slave5OutputCurrentValue 25}
	
slave5OutputCurrentValueTwentysix OBJECT-TYPE
    SYNTAX      DisplayString
    MAX-ACCESS  read-write
    STATUS      current
    DESCRIPTION
	"The second output name of slave5"
    ::= { slave5OutputCurrentValue 26}
	
slave5OutputCurrentValueTwentyseven OBJECT-TYPE
    SYNTAX      DisplayString
    MAX-ACCESS  read-write
    STATUS      current
    DESCRIPTION
	"The second output name of slave5"
    ::= { slave5OutputCurrentValue 27}
	
slave5OutputCurrentValueTwentyeight OBJECT-TYPE
    SYNTAX      DisplayString
    MAX-ACCESS  read-write
    STATUS      current
    DESCRIPTION
	"The second output name of slave5"
    ::= { slave5OutputCurrentValue 28}	
slave5OutputCurrentValueTwentynine OBJECT-TYPE
    SYNTAX      DisplayString
    MAX-ACCESS  read-write
    STATUS      current
    DESCRIPTION
	"The second output name of slave5"
    ::= { slave5OutputCurrentValue 29}
	
slave5OutputCurrentValueThirty OBJECT-TYPE
    SYNTAX      DisplayString
    MAX-ACCESS  read-write
    STATUS      current
    DESCRIPTION
	"The second output name of slave5"
    ::= { slave5OutputCurrentValue 30}
	
slave5OutputCurrentValueThirtyone OBJECT-TYPE
    SYNTAX      DisplayString
    MAX-ACCESS  read-write
    STATUS      current
    DESCRIPTION
	"The second output name of slave5"
    ::= { slave5OutputCurrentValue 31}
	
slave5OutputCurrentValueThirtytwo OBJECT-TYPE
    SYNTAX      DisplayString
    MAX-ACCESS  read-write
    STATUS      current
    DESCRIPTION
	"The second output name of slave5"
    ::= { slave5OutputCurrentValue 32}
	
slave5OutputCurrentValueThirtythree OBJECT-TYPE
    SYNTAX      DisplayString
    MAX-ACCESS  read-write
    STATUS      current
    DESCRIPTION
	"The second output name of slave5"
    ::= { slave5OutputCurrentValue 33}
	
slave5OutputCurrentValueThirtyfour OBJECT-TYPE
    SYNTAX      DisplayString
    MAX-ACCESS  read-write
    STATUS      current
    DESCRIPTION
	"The second output name of slave5"
    ::= { slave5OutputCurrentValue 34}
	
slave5OutputCurrentValueThirtyfive OBJECT-TYPE
    SYNTAX      DisplayString
    MAX-ACCESS  read-write
    STATUS      current
    DESCRIPTION
	"The second output name of slave5"
    ::= { slave5OutputCurrentValue 35}
	
slave5OutputCurrentValueThirtysix OBJECT-TYPE
    SYNTAX      DisplayString
    MAX-ACCESS  read-write
    STATUS      current
    DESCRIPTION
	"The second output name of slave5"
    ::= { slave5OutputCurrentValue 36}
	
slave5OutputCurrentValueThirtyseven OBJECT-TYPE
    SYNTAX      DisplayString
    MAX-ACCESS  read-write
    STATUS      current
    DESCRIPTION
	"The second output name of slave5"
    ::= { slave5OutputCurrentValue 37}
	
slave5OutputCurrentValueThirtyeight OBJECT-TYPE
    SYNTAX      DisplayString
    MAX-ACCESS  read-write
    STATUS      current
    DESCRIPTION
	"The second output name of slave5"
    ::= { slave5OutputCurrentValue 38}
	
slave5OutputCurrentValueThirtynine OBJECT-TYPE
    SYNTAX      DisplayString
    MAX-ACCESS  read-write
    STATUS      current
    DESCRIPTION
	"The second output name of slave5"
    ::= { slave5OutputCurrentValue 39}
	
slave5OutputCurrentValueFourty OBJECT-TYPE
    SYNTAX      DisplayString
    MAX-ACCESS  read-write
    STATUS      current
    DESCRIPTION
	"The second output name of slave5"
    ::= { slave5OutputCurrentValue 40}
	
slave5OutputCurrentValueFourtyone OBJECT-TYPE
    SYNTAX      DisplayString
    MAX-ACCESS  read-write
    STATUS      current
    DESCRIPTION
	"The second output name of slave5"
    ::= { slave5OutputCurrentValue 41}
	
slave5OutputCurrentValueFourtytwo OBJECT-TYPE
    SYNTAX      DisplayString
    MAX-ACCESS  read-write
    STATUS      current
    DESCRIPTION
	"The second output name of slave5"
    ::= { slave5OutputCurrentValue 42}


-------------------------------slave5 output current Min------------------------			
slave5OutputCurrentMin OBJECT IDENTIFIER ::= { slave5OutputCurrent 2}	

slave5OutputCurrentMinOne OBJECT-TYPE
    SYNTAX      DisplayString
    MAX-ACCESS  read-write
    STATUS      current
    DESCRIPTION
	"The first output Min. current alarm value of slave5"
    ::= { slave5OutputCurrentMin 1}

slave5OutputCurrentMinTwo OBJECT-TYPE
    SYNTAX      DisplayString
    MAX-ACCESS  read-write
    STATUS      current
    DESCRIPTION
	"The second output Min. current alarm value of slave5"
    ::= { slave5OutputCurrentMin 2}

slave5OutputCurrentMinThree OBJECT-TYPE
    SYNTAX      DisplayString
    MAX-ACCESS  read-write
    STATUS      current
    DESCRIPTION
	"The second output Min. current alarm value of slave5"
    ::= { slave5OutputCurrentMin 3}

slave5OutputCurrentMinFour OBJECT-TYPE
    SYNTAX      DisplayString
    MAX-ACCESS  read-write
    STATUS      current
    DESCRIPTION
	"The second output Min. current alarm value of slave5"
    ::= { slave5OutputCurrentMin 4}

slave5OutputCurrentMinFive OBJECT-TYPE
    SYNTAX      DisplayString
    MAX-ACCESS  read-write
    STATUS      current
    DESCRIPTION
	"The second output Min. current alarm value of slave5"
    ::= { slave5OutputCurrentMin 5}

slave5OutputCurrentMinSix OBJECT-TYPE
    SYNTAX      DisplayString
    MAX-ACCESS  read-write
    STATUS      current
    DESCRIPTION
	"The second output Min. current alarm value of slave5"
    ::= { slave5OutputCurrentMin 6}

slave5OutputCurrentMinSeven OBJECT-TYPE
    SYNTAX      DisplayString
    MAX-ACCESS  read-write
    STATUS      current
    DESCRIPTION
	"The second output Min. current alarm value of slave5"
    ::= { slave5OutputCurrentMin 7}

slave5OutputCurrentMinEight OBJECT-TYPE
    SYNTAX      DisplayString
    MAX-ACCESS  read-write
    STATUS      current
    DESCRIPTION
	"The second output Min. current alarm value of slave5"
    ::= { slave5OutputCurrentMin 8}

slave5OutputCurrentMinNine OBJECT-TYPE
    SYNTAX      DisplayString
    MAX-ACCESS  read-write
    STATUS      current
    DESCRIPTION
	"The second output Min. current alarm value of slave5"
    ::= { slave5OutputCurrentMin 9}

slave5OutputCurrentMinTen OBJECT-TYPE
    SYNTAX      DisplayString
    MAX-ACCESS  read-write
    STATUS      current
    DESCRIPTION
	"The second output Min. current alarm value of slave5"
    ::= { slave5OutputCurrentMin 10}

slave5OutputCurrentMinEleven OBJECT-TYPE
    SYNTAX      DisplayString
    MAX-ACCESS  read-write
    STATUS      current
    DESCRIPTION
	"The second output Min. current alarm value of slave5"
    ::= { slave5OutputCurrentMin 11}

slave5OutputCurrentMinTwel OBJECT-TYPE
    SYNTAX      DisplayString
    MAX-ACCESS  read-write
    STATUS      current
    DESCRIPTION
	"The second output Min. current alarm value of slave5"
    ::= { slave5OutputCurrentMin 12}

slave5OutputCurrentMinThirteen OBJECT-TYPE
    SYNTAX      DisplayString
    MAX-ACCESS  read-write
    STATUS      current
    DESCRIPTION
	"The second output Min. current alarm value of slave5"
    ::= { slave5OutputCurrentMin 13}

slave5OutputCurrentMinFourteen OBJECT-TYPE
    SYNTAX      DisplayString
    MAX-ACCESS  read-write
    STATUS      current
    DESCRIPTION
	"The second output Min. current alarm value of slave5"
    ::= { slave5OutputCurrentMin 14}

slave5OutputCurrentMinFifteen OBJECT-TYPE
    SYNTAX      DisplayString
    MAX-ACCESS  read-write
    STATUS      current
    DESCRIPTION
	"The second output Min. current alarm value of slave5"
    ::= { slave5OutputCurrentMin 15}

slave5OutputCurrentMinSixteen OBJECT-TYPE
    SYNTAX      DisplayString
    MAX-ACCESS  read-write
    STATUS      current
    DESCRIPTION
	"The second output Min. current alarm value of slave5"
    ::= { slave5OutputCurrentMin 16}

slave5OutputCurrentMinSeventeen OBJECT-TYPE
    SYNTAX      DisplayString
    MAX-ACCESS  read-write
    STATUS      current
    DESCRIPTION
	"The second output Min. current alarm value of slave5"
    ::= { slave5OutputCurrentMin 17}

slave5OutputCurrentMinEighteen OBJECT-TYPE
    SYNTAX      DisplayString
    MAX-ACCESS  read-write
    STATUS      current
    DESCRIPTION
	"The second output Min. current alarm value of slave5"
    ::= { slave5OutputCurrentMin 18}
	
slave5OutputCurrentMinNineteen OBJECT-TYPE
    SYNTAX      DisplayString
    MAX-ACCESS  read-write
    STATUS      current
    DESCRIPTION
	"The second output Min. current alarm value of slave5"
    ::= { slave5OutputCurrentMin 19}
	
slave5OutputCurrentMintwenty OBJECT-TYPE
    SYNTAX      DisplayString
    MAX-ACCESS  read-write
    STATUS      current
    DESCRIPTION
	"The second output Min. current alarm value of slave5"
    ::= { slave5OutputCurrentMin 20}
	
slave5OutputCurrentMinTwentyone OBJECT-TYPE
    SYNTAX      DisplayString
    MAX-ACCESS  read-write
    STATUS      current
    DESCRIPTION
	"The second output Min. current alarm value of slave5"
    ::= { slave5OutputCurrentMin 21}
	
slave5OutputCurrentMinTwentyonetwo OBJECT-TYPE
    SYNTAX      DisplayString
    MAX-ACCESS  read-write
    STATUS      current
    DESCRIPTION
	"The second output Min. current alarm value of slave5"
    ::= { slave5OutputCurrentMin 22}
	
slave5OutputCurrentMinTwentythree OBJECT-TYPE
    SYNTAX      DisplayString
    MAX-ACCESS  read-write
    STATUS      current
    DESCRIPTION
	"The second output Min. current alarm value of slave5"
    ::= { slave5OutputCurrentMin 23}
	
slave5OutputCurrentMinTwentyfour OBJECT-TYPE
    SYNTAX      DisplayString
    MAX-ACCESS  read-write
    STATUS      current
    DESCRIPTION
	"The second output Min. current alarm value of slave5"
    ::= { slave5OutputCurrentMin 24}
	
slave5OutputCurrentMinTwentyfive OBJECT-TYPE
    SYNTAX      DisplayString
    MAX-ACCESS  read-write
    STATUS      current
    DESCRIPTION
	"The second output Min. current alarm value of slave5"
    ::= { slave5OutputCurrentMin 25}
	
slave5OutputCurrentMinTwentysix OBJECT-TYPE
    SYNTAX      DisplayString
    MAX-ACCESS  read-write
    STATUS      current
    DESCRIPTION
	"The second output Min. current alarm value of slave5"
    ::= { slave5OutputCurrentMin 26}
	
slave5OutputCurrentMinTwentyseven OBJECT-TYPE
    SYNTAX      DisplayString
    MAX-ACCESS  read-write
    STATUS      current
    DESCRIPTION
	"The second output Min. current alarm value of slave5"
    ::= { slave5OutputCurrentMin 27}
	
slave5OutputCurrentMinTwentyeight OBJECT-TYPE
    SYNTAX      DisplayString
    MAX-ACCESS  read-write
    STATUS      current
    DESCRIPTION
	"The second output Min. current alarm value of slave5"
    ::= { slave5OutputCurrentMin 28}	
slave5OutputCurrentMinTwentynine OBJECT-TYPE
    SYNTAX      DisplayString
    MAX-ACCESS  read-write
    STATUS      current
    DESCRIPTION
	"The second output Min. current alarm value of slave5"
    ::= { slave5OutputCurrentMin 29}
	
slave5OutputCurrentMinThirty OBJECT-TYPE
    SYNTAX      DisplayString
    MAX-ACCESS  read-write
    STATUS      current
    DESCRIPTION
	"The second output Min. current alarm value of slave5"
    ::= { slave5OutputCurrentMin 30}
	
slave5OutputCurrentMinThirtyone OBJECT-TYPE
    SYNTAX      DisplayString
    MAX-ACCESS  read-write
    STATUS      current
    DESCRIPTION
	"The second output Min. current alarm value of slave5"
    ::= { slave5OutputCurrentMin 31}
	
slave5OutputCurrentMinThirtytwo OBJECT-TYPE
    SYNTAX      DisplayString
    MAX-ACCESS  read-write
    STATUS      current
    DESCRIPTION
	"The second output Min. current alarm value of slave5"
    ::= { slave5OutputCurrentMin 32}
	
slave5OutputCurrentMinThirtythree OBJECT-TYPE
    SYNTAX      DisplayString
    MAX-ACCESS  read-write
    STATUS      current
    DESCRIPTION
	"The second output Min. current alarm value of slave5"
    ::= { slave5OutputCurrentMin 33}
	
slave5OutputCurrentMinThirtyfour OBJECT-TYPE
    SYNTAX      DisplayString
    MAX-ACCESS  read-write
    STATUS      current
    DESCRIPTION
	"The second output Min. current alarm value of slave5"
    ::= { slave5OutputCurrentMin 34}
	
slave5OutputCurrentMinThirtyfive OBJECT-TYPE
    SYNTAX      DisplayString
    MAX-ACCESS  read-write
    STATUS      current
    DESCRIPTION
	"The second output Min. current alarm value of slave5"
    ::= { slave5OutputCurrentMin 35}
	
slave5OutputCurrentMinThirtysix OBJECT-TYPE
    SYNTAX      DisplayString
    MAX-ACCESS  read-write
    STATUS      current
    DESCRIPTION
	"The second output Min. current alarm value of slave5"
    ::= { slave5OutputCurrentMin 36}
	
slave5OutputCurrentMinThirtyseven OBJECT-TYPE
    SYNTAX      DisplayString
    MAX-ACCESS  read-write
    STATUS      current
    DESCRIPTION
	"The second output Min. current alarm value of slave5"
    ::= { slave5OutputCurrentMin 37}
	
slave5OutputCurrentMinThirtyeight OBJECT-TYPE
    SYNTAX      DisplayString
    MAX-ACCESS  read-write
    STATUS      current
    DESCRIPTION
	"The second output Min. current alarm value of slave5"
    ::= { slave5OutputCurrentMin 38}
	
slave5OutputCurrentMinThirtynine OBJECT-TYPE
    SYNTAX      DisplayString
    MAX-ACCESS  read-write
    STATUS      current
    DESCRIPTION
	"The second output Min. current alarm value of slave5"
    ::= { slave5OutputCurrentMin 39}
	
slave5OutputCurrentMinFourty OBJECT-TYPE
    SYNTAX      DisplayString
    MAX-ACCESS  read-write
    STATUS      current
    DESCRIPTION
	"The second output Min. current alarm value of slave5"
    ::= { slave5OutputCurrentMin 40}
	
slave5OutputCurrentMinFourtyone OBJECT-TYPE
    SYNTAX      DisplayString
    MAX-ACCESS  read-write
    STATUS      current
    DESCRIPTION
	"The second output Min. current alarm value of slave5"
    ::= { slave5OutputCurrentMin 41}
	
slave5OutputCurrentMinFourtytwo OBJECT-TYPE
    SYNTAX      DisplayString
    MAX-ACCESS  read-write
    STATUS      current
    DESCRIPTION
	"The second output Min. current alarm value of slave5"
    ::= { slave5OutputCurrentMin 42}


------------------------slave5 output current Min critical----------------			
slave5OutputCurrentMinCritical OBJECT IDENTIFIER ::= { slave5OutputCurrent 3}	

slave5OutputCurrentMinCriticalOne OBJECT-TYPE
    SYNTAX      DisplayString
    MAX-ACCESS  read-write
    STATUS      current
    DESCRIPTION
	"The first output Min. current warning value of slave5"
    ::= { slave5OutputCurrentMinCritical 1}

slave5OutputCurrentMinCriticalTwo OBJECT-TYPE
    SYNTAX      DisplayString
    MAX-ACCESS  read-write
    STATUS      current
    DESCRIPTION
	"The second output Min. current warning value of slave5"
    ::= { slave5OutputCurrentMinCritical 2}

slave5OutputCurrentMinCriticalThree OBJECT-TYPE
    SYNTAX      DisplayString
    MAX-ACCESS  read-write
    STATUS      current
    DESCRIPTION
	"The second output Min. current warning value of slave5"
    ::= { slave5OutputCurrentMinCritical 3}

slave5OutputCurrentMinCriticalFour OBJECT-TYPE
    SYNTAX      DisplayString
    MAX-ACCESS  read-write
    STATUS      current
    DESCRIPTION
	"The second output Min. current warning value of slave5"
    ::= { slave5OutputCurrentMinCritical 4}

slave5OutputCurrentMinCriticalFive OBJECT-TYPE
    SYNTAX      DisplayString
    MAX-ACCESS  read-write
    STATUS      current
    DESCRIPTION
	"The second output Min. current warning value of slave5"
    ::= { slave5OutputCurrentMinCritical 5}

slave5OutputCurrentMinCriticalSix OBJECT-TYPE
    SYNTAX      DisplayString
    MAX-ACCESS  read-write
    STATUS      current
    DESCRIPTION
	"The second output Min. current warning value of slave5"
    ::= { slave5OutputCurrentMinCritical 6}

slave5OutputCurrentMinCriticalSeven OBJECT-TYPE
    SYNTAX      DisplayString
    MAX-ACCESS  read-write
    STATUS      current
    DESCRIPTION
	"The second output Min. current warning value of slave5"
    ::= { slave5OutputCurrentMinCritical 7}

slave5OutputCurrentMinCriticalEight OBJECT-TYPE
    SYNTAX      DisplayString
    MAX-ACCESS  read-write
    STATUS      current
    DESCRIPTION
	"The second output Min. current warning value of slave5"
    ::= { slave5OutputCurrentMinCritical 8}

slave5OutputCurrentMinCriticalNine OBJECT-TYPE
    SYNTAX      DisplayString
    MAX-ACCESS  read-write
    STATUS      current
    DESCRIPTION
	"The second output Min. current warning value of slave5"
    ::= { slave5OutputCurrentMinCritical 9}

slave5OutputCurrentMinCriticalTen OBJECT-TYPE
    SYNTAX      DisplayString
    MAX-ACCESS  read-write
    STATUS      current
    DESCRIPTION
	"The second output Min. current warning value of slave5"
    ::= { slave5OutputCurrentMinCritical 10}

slave5OutputCurrentMinCriticalEleven OBJECT-TYPE
    SYNTAX      DisplayString
    MAX-ACCESS  read-write
    STATUS      current
    DESCRIPTION
	"The second output Min. current warning value of slave5"
    ::= { slave5OutputCurrentMinCritical 11}

slave5OutputCurrentMinCriticalTwel OBJECT-TYPE
    SYNTAX      DisplayString
    MAX-ACCESS  read-write
    STATUS      current
    DESCRIPTION
	"The second output Min. current warning value of slave5"
    ::= { slave5OutputCurrentMinCritical 12}

slave5OutputCurrentMinCriticalThirteen OBJECT-TYPE
    SYNTAX      DisplayString
    MAX-ACCESS  read-write
    STATUS      current
    DESCRIPTION
	"The second output Min. current warning value of slave5"
    ::= { slave5OutputCurrentMinCritical 13}

slave5OutputCurrentMinCriticalFourteen OBJECT-TYPE
    SYNTAX      DisplayString
    MAX-ACCESS  read-write
    STATUS      current
    DESCRIPTION
	"The second output Min. current warning value of slave5"
    ::= { slave5OutputCurrentMinCritical 14}

slave5OutputCurrentMinCriticalFifteen OBJECT-TYPE
    SYNTAX      DisplayString
    MAX-ACCESS  read-write
    STATUS      current
    DESCRIPTION
	"The second output Min. current warning value of slave5"
    ::= { slave5OutputCurrentMinCritical 15}

slave5OutputCurrentMinCriticalSixteen OBJECT-TYPE
    SYNTAX      DisplayString
    MAX-ACCESS  read-write
    STATUS      current
    DESCRIPTION
	"The second output Min. current warning value of slave5"
    ::= { slave5OutputCurrentMinCritical 16}

slave5OutputCurrentMinCriticalSeventeen OBJECT-TYPE
    SYNTAX      DisplayString
    MAX-ACCESS  read-write
    STATUS      current
    DESCRIPTION
	"The second output Min. current warning value of slave5"
    ::= { slave5OutputCurrentMinCritical 17}

slave5OutputCurrentMinCriticalEighteen OBJECT-TYPE
    SYNTAX      DisplayString
    MAX-ACCESS  read-write
    STATUS      current
    DESCRIPTION
	"The second output Min. current warning value of slave5"
    ::= { slave5OutputCurrentMinCritical 18}
	
slave5OutputCurrentMinCriticalNineteen OBJECT-TYPE
    SYNTAX      DisplayString
    MAX-ACCESS  read-write
    STATUS      current
    DESCRIPTION
	"The second output Min. current warning value of slave5"
    ::= { slave5OutputCurrentMinCritical 19}
	
slave5OutputCurrentMinCriticaltwenty OBJECT-TYPE
    SYNTAX      DisplayString
    MAX-ACCESS  read-write
    STATUS      current
    DESCRIPTION
	"The second output Min. current warning value of slave5"
    ::= { slave5OutputCurrentMinCritical 20}
	
slave5OutputCurrentMinCriticalTwentyone OBJECT-TYPE
    SYNTAX      DisplayString
    MAX-ACCESS  read-write
    STATUS      current
    DESCRIPTION
	"The second output Min. current warning value of slave5"
    ::= { slave5OutputCurrentMinCritical 21}
	
slave5OutputCurrentMinCriticalTwentyonetwo OBJECT-TYPE
    SYNTAX      DisplayString
    MAX-ACCESS  read-write
    STATUS      current
    DESCRIPTION
	"The second output Min. current warning value of slave5"
    ::= { slave5OutputCurrentMinCritical 22}
	
slave5OutputCurrentMinCriticalTwentythree OBJECT-TYPE
    SYNTAX      DisplayString
    MAX-ACCESS  read-write
    STATUS      current
    DESCRIPTION
	"The second output Min. current warning value of slave5"
    ::= { slave5OutputCurrentMinCritical 23}
	
slave5OutputCurrentMinCriticalTwentyfour OBJECT-TYPE
    SYNTAX      DisplayString
    MAX-ACCESS  read-write
    STATUS      current
    DESCRIPTION
	"The second output Min. current warning value of slave5"
    ::= { slave5OutputCurrentMinCritical 24}
	
slave5OutputCurrentMinCriticalTwentyfive OBJECT-TYPE
    SYNTAX      DisplayString
    MAX-ACCESS  read-write
    STATUS      current
    DESCRIPTION
	"The second output Min. current warning value of slave5"
    ::= { slave5OutputCurrentMinCritical 25}
	
slave5OutputCurrentMinCriticalTwentysix OBJECT-TYPE
    SYNTAX      DisplayString
    MAX-ACCESS  read-write
    STATUS      current
    DESCRIPTION
	"The second output Min. current warning value of slave5"
    ::= { slave5OutputCurrentMinCritical 26}
	
slave5OutputCurrentMinCriticalTwentyseven OBJECT-TYPE
    SYNTAX      DisplayString
    MAX-ACCESS  read-write
    STATUS      current
    DESCRIPTION
	"The second output Min. current warning value of slave5"
    ::= { slave5OutputCurrentMinCritical 27}
	
slave5OutputCurrentMinCriticalTwentyeight OBJECT-TYPE
    SYNTAX      DisplayString
    MAX-ACCESS  read-write
    STATUS      current
    DESCRIPTION
	"The second output Min. current warning value of slave5"
    ::= { slave5OutputCurrentMinCritical 28}	
slave5OutputCurrentMinCriticalTwentynine OBJECT-TYPE
    SYNTAX      DisplayString
    MAX-ACCESS  read-write
    STATUS      current
    DESCRIPTION
	"The second output Min. current warning value of slave5"
    ::= { slave5OutputCurrentMinCritical 29}
	
slave5OutputCurrentMinCriticalThirty OBJECT-TYPE
    SYNTAX      DisplayString
    MAX-ACCESS  read-write
    STATUS      current
    DESCRIPTION
	"The second output Min. current warning value of slave5"
    ::= { slave5OutputCurrentMinCritical 30}
	
slave5OutputCurrentMinCriticalThirtyone OBJECT-TYPE
    SYNTAX      DisplayString
    MAX-ACCESS  read-write
    STATUS      current
    DESCRIPTION
	"The second output Min. current warning value of slave5"
    ::= { slave5OutputCurrentMinCritical 31}
	
slave5OutputCurrentMinCriticalThirtytwo OBJECT-TYPE
    SYNTAX      DisplayString
    MAX-ACCESS  read-write
    STATUS      current
    DESCRIPTION
	"The second output Min. current warning value of slave5"
    ::= { slave5OutputCurrentMinCritical 32}
	
slave5OutputCurrentMinCriticalThirtythree OBJECT-TYPE
    SYNTAX      DisplayString
    MAX-ACCESS  read-write
    STATUS      current
    DESCRIPTION
	"The second output Min. current warning value of slave5"
    ::= { slave5OutputCurrentMinCritical 33}
	
slave5OutputCurrentMinCriticalThirtyfour OBJECT-TYPE
    SYNTAX      DisplayString
    MAX-ACCESS  read-write
    STATUS      current
    DESCRIPTION
	"The second output Min. current warning value of slave5"
    ::= { slave5OutputCurrentMinCritical 34}
	
slave5OutputCurrentMinCriticalThirtyfive OBJECT-TYPE
    SYNTAX      DisplayString
    MAX-ACCESS  read-write
    STATUS      current
    DESCRIPTION
	"The second output Min. current warning value of slave5"
    ::= { slave5OutputCurrentMinCritical 35}
	
slave5OutputCurrentMinCriticalThirtysix OBJECT-TYPE
    SYNTAX      DisplayString
    MAX-ACCESS  read-write
    STATUS      current
    DESCRIPTION
	"The second output Min. current warning value of slave5"
    ::= { slave5OutputCurrentMinCritical 36}
	
slave5OutputCurrentMinCriticalThirtyseven OBJECT-TYPE
    SYNTAX      DisplayString
    MAX-ACCESS  read-write
    STATUS      current
    DESCRIPTION
	"The second output Min. current warning value of slave5"
    ::= { slave5OutputCurrentMinCritical 37}
	
slave5OutputCurrentMinCriticalThirtyeight OBJECT-TYPE
    SYNTAX      DisplayString
    MAX-ACCESS  read-write
    STATUS      current
    DESCRIPTION
	"The second output Min. current warning value of slave5"
    ::= { slave5OutputCurrentMinCritical 38}
	
slave5OutputCurrentMinCriticalThirtynine OBJECT-TYPE
    SYNTAX      DisplayString
    MAX-ACCESS  read-write
    STATUS      current
    DESCRIPTION
	"The second output Min. current warning value of slave5"
    ::= { slave5OutputCurrentMinCritical 39}
	
slave5OutputCurrentMinCriticalFourty OBJECT-TYPE
    SYNTAX      DisplayString
    MAX-ACCESS  read-write
    STATUS      current
    DESCRIPTION
	"The second output Min. current warning value of slave5"
    ::= { slave5OutputCurrentMinCritical 40}
	
slave5OutputCurrentMinCriticalFourtyone OBJECT-TYPE
    SYNTAX      DisplayString
    MAX-ACCESS  read-write
    STATUS      current
    DESCRIPTION
	"The second output Min. current warning value of slave5"
    ::= { slave5OutputCurrentMinCritical 41}
	
slave5OutputCurrentMinCriticalFourtytwo OBJECT-TYPE
    SYNTAX      DisplayString
    MAX-ACCESS  read-write
    STATUS      current
    DESCRIPTION
	"The second output Min. current warning value of slave5"
    ::= { slave5OutputCurrentMinCritical 42}
	
	
------------------------slave5 output current Max critical----------------			
slave5OutputCurrentMaxCritical OBJECT IDENTIFIER ::= { slave5OutputCurrent 4}	

slave5OutputCurrentMaxCriticalOne OBJECT-TYPE
    SYNTAX      DisplayString
    MAX-ACCESS  read-write
    STATUS      current
    DESCRIPTION
	"The first output Max. current warning value of slave5"
    ::= { slave5OutputCurrentMaxCritical 1}

slave5OutputCurrentMaxCriticalTwo OBJECT-TYPE
    SYNTAX      DisplayString
    MAX-ACCESS  read-write
    STATUS      current
    DESCRIPTION
	"The second output Max. current warning value of slave5"
    ::= { slave5OutputCurrentMaxCritical 2}

slave5OutputCurrentMaxCriticalThree OBJECT-TYPE
    SYNTAX      DisplayString
    MAX-ACCESS  read-write
    STATUS      current
    DESCRIPTION
	"The second output Max. current warning value of slave5"
    ::= { slave5OutputCurrentMaxCritical 3}

slave5OutputCurrentMaxCriticalFour OBJECT-TYPE
    SYNTAX      DisplayString
    MAX-ACCESS  read-write
    STATUS      current
    DESCRIPTION
	"The second output Max. current warning value of slave5"
    ::= { slave5OutputCurrentMaxCritical 4}

slave5OutputCurrentMaxCriticalFive OBJECT-TYPE
    SYNTAX      DisplayString
    MAX-ACCESS  read-write
    STATUS      current
    DESCRIPTION
	"The second output Max. current warning value of slave5"
    ::= { slave5OutputCurrentMaxCritical 5}

slave5OutputCurrentMaxCriticalSix OBJECT-TYPE
    SYNTAX      DisplayString
    MAX-ACCESS  read-write
    STATUS      current
    DESCRIPTION
	"The second output Max. current warning value of slave5"
    ::= { slave5OutputCurrentMaxCritical 6}

slave5OutputCurrentMaxCriticalSeven OBJECT-TYPE
    SYNTAX      DisplayString
    MAX-ACCESS  read-write
    STATUS      current
    DESCRIPTION
	"The second output Max. current warning value of slave5"
    ::= { slave5OutputCurrentMaxCritical 7}

slave5OutputCurrentMaxCriticalEight OBJECT-TYPE
    SYNTAX      DisplayString
    MAX-ACCESS  read-write
    STATUS      current
    DESCRIPTION
	"The second output Max. current warning value of slave5"
    ::= { slave5OutputCurrentMaxCritical 8}

slave5OutputCurrentMaxCriticalNine OBJECT-TYPE
    SYNTAX      DisplayString
    MAX-ACCESS  read-write
    STATUS      current
    DESCRIPTION
	"The second output Max. current warning value of slave5"
    ::= { slave5OutputCurrentMaxCritical 9}

slave5OutputCurrentMaxCriticalTen OBJECT-TYPE
    SYNTAX      DisplayString
    MAX-ACCESS  read-write
    STATUS      current
    DESCRIPTION
	"The second output Max. current warning value of slave5"
    ::= { slave5OutputCurrentMaxCritical 10}

slave5OutputCurrentMaxCriticalEleven OBJECT-TYPE
    SYNTAX      DisplayString
    MAX-ACCESS  read-write
    STATUS      current
    DESCRIPTION
	"The second output Max. current warning value of slave5"
    ::= { slave5OutputCurrentMaxCritical 11}

slave5OutputCurrentMaxCriticalTwel OBJECT-TYPE
    SYNTAX      DisplayString
    MAX-ACCESS  read-write
    STATUS      current
    DESCRIPTION
	"The second output Max. current warning value of slave5"
    ::= { slave5OutputCurrentMaxCritical 12}

slave5OutputCurrentMaxCriticalThirteen OBJECT-TYPE
    SYNTAX      DisplayString
    MAX-ACCESS  read-write
    STATUS      current
    DESCRIPTION
	"The second output Max. current warning value of slave5"
    ::= { slave5OutputCurrentMaxCritical 13}

slave5OutputCurrentMaxCriticalFourteen OBJECT-TYPE
    SYNTAX      DisplayString
    MAX-ACCESS  read-write
    STATUS      current
    DESCRIPTION
	"The second output Max. current warning value of slave5"
    ::= { slave5OutputCurrentMaxCritical 14}

slave5OutputCurrentMaxCriticalFifteen OBJECT-TYPE
    SYNTAX      DisplayString
    MAX-ACCESS  read-write
    STATUS      current
    DESCRIPTION
	"The second output Max. current warning value of slave5"
    ::= { slave5OutputCurrentMaxCritical 15}

slave5OutputCurrentMaxCriticalSixteen OBJECT-TYPE
    SYNTAX      DisplayString
    MAX-ACCESS  read-write
    STATUS      current
    DESCRIPTION
	"The second output Max. current warning value of slave5"
    ::= { slave5OutputCurrentMaxCritical 16}

slave5OutputCurrentMaxCriticalSeventeen OBJECT-TYPE
    SYNTAX      DisplayString
    MAX-ACCESS  read-write
    STATUS      current
    DESCRIPTION
	"The second output Max. current warning value of slave5"
    ::= { slave5OutputCurrentMaxCritical 17}

slave5OutputCurrentMaxCriticalEighteen OBJECT-TYPE
    SYNTAX      DisplayString
    MAX-ACCESS  read-write
    STATUS      current
    DESCRIPTION
	"The second output Max. current warning value of slave5"
    ::= { slave5OutputCurrentMaxCritical 18}
	
slave5OutputCurrentMaxCriticalNineteen OBJECT-TYPE
    SYNTAX      DisplayString
    MAX-ACCESS  read-write
    STATUS      current
    DESCRIPTION
	"The second output Max. current warning value of slave5"
    ::= { slave5OutputCurrentMaxCritical 19}
	
slave5OutputCurrentMaxCriticaltwenty OBJECT-TYPE
    SYNTAX      DisplayString
    MAX-ACCESS  read-write
    STATUS      current
    DESCRIPTION
	"The second output Max. current warning value of slave5"
    ::= { slave5OutputCurrentMaxCritical 20}
	
slave5OutputCurrentMaxCriticalTwentyone OBJECT-TYPE
    SYNTAX      DisplayString
    MAX-ACCESS  read-write
    STATUS      current
    DESCRIPTION
	"The second output Max. current warning value of slave5"
    ::= { slave5OutputCurrentMaxCritical 21}
	
slave5OutputCurrentMaxCriticalTwentyonetwo OBJECT-TYPE
    SYNTAX      DisplayString
    MAX-ACCESS  read-write
    STATUS      current
    DESCRIPTION
	"The second output Max. current warning value of slave5"
    ::= { slave5OutputCurrentMaxCritical 22}
	
slave5OutputCurrentMaxCriticalTwentythree OBJECT-TYPE
    SYNTAX      DisplayString
    MAX-ACCESS  read-write
    STATUS      current
    DESCRIPTION
	"The second output Max. current warning value of slave5"
    ::= { slave5OutputCurrentMaxCritical 23}
	
slave5OutputCurrentMaxCriticalTwentyfour OBJECT-TYPE
    SYNTAX      DisplayString
    MAX-ACCESS  read-write
    STATUS      current
    DESCRIPTION
	"The second output Max. current warning value of slave5"
    ::= { slave5OutputCurrentMaxCritical 24}
	
slave5OutputCurrentMaxCriticalTwentyfive OBJECT-TYPE
    SYNTAX      DisplayString
    MAX-ACCESS  read-write
    STATUS      current
    DESCRIPTION
	"The second output Max. current warning value of slave5"
    ::= { slave5OutputCurrentMaxCritical 25}
	
slave5OutputCurrentMaxCriticalTwentysix OBJECT-TYPE
    SYNTAX      DisplayString
    MAX-ACCESS  read-write
    STATUS      current
    DESCRIPTION
	"The second output Max. current warning value of slave5"
    ::= { slave5OutputCurrentMaxCritical 26}
	
slave5OutputCurrentMaxCriticalTwentyseven OBJECT-TYPE
    SYNTAX      DisplayString
    MAX-ACCESS  read-write
    STATUS      current
    DESCRIPTION
	"The second output Max. current warning value of slave5"
    ::= { slave5OutputCurrentMaxCritical 27}
	
slave5OutputCurrentMaxCriticalTwentyeight OBJECT-TYPE
    SYNTAX      DisplayString
    MAX-ACCESS  read-write
    STATUS      current
    DESCRIPTION
	"The second output Max. current warning value of slave5"
    ::= { slave5OutputCurrentMaxCritical 28}	
slave5OutputCurrentMaxCriticalTwentynine OBJECT-TYPE
    SYNTAX      DisplayString
    MAX-ACCESS  read-write
    STATUS      current
    DESCRIPTION
	"The second output Max. current warning value of slave5"
    ::= { slave5OutputCurrentMaxCritical 29}
	
slave5OutputCurrentMaxCriticalThirty OBJECT-TYPE
    SYNTAX      DisplayString
    MAX-ACCESS  read-write
    STATUS      current
    DESCRIPTION
	"The second output Max. current warning value of slave5"
    ::= { slave5OutputCurrentMaxCritical 30}
	
slave5OutputCurrentMaxCriticalThirtyone OBJECT-TYPE
    SYNTAX      DisplayString
    MAX-ACCESS  read-write
    STATUS      current
    DESCRIPTION
	"The second output Max. current warning value of slave5"
    ::= { slave5OutputCurrentMaxCritical 31}
	
slave5OutputCurrentMaxCriticalThirtytwo OBJECT-TYPE
    SYNTAX      DisplayString
    MAX-ACCESS  read-write
    STATUS      current
    DESCRIPTION
	"The second output Max. current warning value of slave5"
    ::= { slave5OutputCurrentMaxCritical 32}
	
slave5OutputCurrentMaxCriticalThirtythree OBJECT-TYPE
    SYNTAX      DisplayString
    MAX-ACCESS  read-write
    STATUS      current
    DESCRIPTION
	"The second output Max. current warning value of slave5"
    ::= { slave5OutputCurrentMaxCritical 33}
	
slave5OutputCurrentMaxCriticalThirtyfour OBJECT-TYPE
    SYNTAX      DisplayString
    MAX-ACCESS  read-write
    STATUS      current
    DESCRIPTION
	"The second output Max. current warning value of slave5"
    ::= { slave5OutputCurrentMaxCritical 34}
	
slave5OutputCurrentMaxCriticalThirtyfive OBJECT-TYPE
    SYNTAX      DisplayString
    MAX-ACCESS  read-write
    STATUS      current
    DESCRIPTION
	"The second output Max. current warning value of slave5"
    ::= { slave5OutputCurrentMaxCritical 35}
	
slave5OutputCurrentMaxCriticalThirtysix OBJECT-TYPE
    SYNTAX      DisplayString
    MAX-ACCESS  read-write
    STATUS      current
    DESCRIPTION
	"The second output Max. current warning value of slave5"
    ::= { slave5OutputCurrentMaxCritical 36}
	
slave5OutputCurrentMaxCriticalThirtyseven OBJECT-TYPE
    SYNTAX      DisplayString
    MAX-ACCESS  read-write
    STATUS      current
    DESCRIPTION
	"The second output Max. current warning value of slave5"
    ::= { slave5OutputCurrentMaxCritical 37}
	
slave5OutputCurrentMaxCriticalThirtyeight OBJECT-TYPE
    SYNTAX      DisplayString
    MAX-ACCESS  read-write
    STATUS      current
    DESCRIPTION
	"The second output Max. current warning value of slave5"
    ::= { slave5OutputCurrentMaxCritical 38}
	
slave5OutputCurrentMaxCriticalThirtynine OBJECT-TYPE
    SYNTAX      DisplayString
    MAX-ACCESS  read-write
    STATUS      current
    DESCRIPTION
	"The second output Max. current warning value of slave5"
    ::= { slave5OutputCurrentMaxCritical 39}
	
slave5OutputCurrentMaxCriticalFourty OBJECT-TYPE
    SYNTAX      DisplayString
    MAX-ACCESS  read-write
    STATUS      current
    DESCRIPTION
	"The second output Max. current warning value of slave5"
    ::= { slave5OutputCurrentMaxCritical 40}
	
slave5OutputCurrentMaxCriticalFourtyone OBJECT-TYPE
    SYNTAX      DisplayString
    MAX-ACCESS  read-write
    STATUS      current
    DESCRIPTION
	"The second output Max. current warning value of slave5"
    ::= { slave5OutputCurrentMaxCritical 41}
	
slave5OutputCurrentMaxCriticalFourtytwo OBJECT-TYPE
    SYNTAX      DisplayString
    MAX-ACCESS  read-write
    STATUS      current
    DESCRIPTION
	"The second output Max. current warning value of slave5"
    ::= { slave5OutputCurrentMaxCritical 42}
	
	
------------------------slave5 output current Max----------------			
slave5OutputCurrentMax OBJECT IDENTIFIER ::= { slave5OutputCurrent 5}
	
slave5OutputCurrentMaxOne OBJECT-TYPE
    SYNTAX      DisplayString
    MAX-ACCESS  read-write
    STATUS      current
    DESCRIPTION
	"The first output Max. current alarm value of slave5"
    ::= { slave5OutputCurrentMax 1}

slave5OutputCurrentMaxTwo OBJECT-TYPE
    SYNTAX      DisplayString
    MAX-ACCESS  read-write
    STATUS      current
    DESCRIPTION
	"The second output Max. current alarm value of slave5"
    ::= { slave5OutputCurrentMax 2}

slave5OutputCurrentMaxThree OBJECT-TYPE
    SYNTAX      DisplayString
    MAX-ACCESS  read-write
    STATUS      current
    DESCRIPTION
	"The second output Max. current alarm value of slave5"
    ::= { slave5OutputCurrentMax 3}

slave5OutputCurrentMaxFour OBJECT-TYPE
    SYNTAX      DisplayString
    MAX-ACCESS  read-write
    STATUS      current
    DESCRIPTION
	"The second output Max. current alarm value of slave5"
    ::= { slave5OutputCurrentMax 4}

slave5OutputCurrentMaxFive OBJECT-TYPE
    SYNTAX      DisplayString
    MAX-ACCESS  read-write
    STATUS      current
    DESCRIPTION
	"The second output Max. current alarm value of slave5"
    ::= { slave5OutputCurrentMax 5}

slave5OutputCurrentMaxSix OBJECT-TYPE
    SYNTAX      DisplayString
    MAX-ACCESS  read-write
    STATUS      current
    DESCRIPTION
	"The second output Max. current alarm value of slave5"
    ::= { slave5OutputCurrentMax 6}

slave5OutputCurrentMaxSeven OBJECT-TYPE
    SYNTAX      DisplayString
    MAX-ACCESS  read-write
    STATUS      current
    DESCRIPTION
	"The second output Max. current alarm value of slave5"
    ::= { slave5OutputCurrentMax 7}

slave5OutputCurrentMaxEight OBJECT-TYPE
    SYNTAX      DisplayString
    MAX-ACCESS  read-write
    STATUS      current
    DESCRIPTION
	"The second output Max. current alarm value of slave5"
    ::= { slave5OutputCurrentMax 8}

slave5OutputCurrentMaxNine OBJECT-TYPE
    SYNTAX      DisplayString
    MAX-ACCESS  read-write
    STATUS      current
    DESCRIPTION
	"The second output Max. current alarm value of slave5"
    ::= { slave5OutputCurrentMax 9}

slave5OutputCurrentMaxTen OBJECT-TYPE
    SYNTAX      DisplayString
    MAX-ACCESS  read-write
    STATUS      current
    DESCRIPTION
	"The second output Max. current alarm value of slave5"
    ::= { slave5OutputCurrentMax 10}

slave5OutputCurrentMaxEleven OBJECT-TYPE
    SYNTAX      DisplayString
    MAX-ACCESS  read-write
    STATUS      current
    DESCRIPTION
	"The second output Max. current alarm value of slave5"
    ::= { slave5OutputCurrentMax 11}

slave5OutputCurrentMaxTwel OBJECT-TYPE
    SYNTAX      DisplayString
    MAX-ACCESS  read-write
    STATUS      current
    DESCRIPTION
	"The second output Max. current alarm value of slave5"
    ::= { slave5OutputCurrentMax 12}

slave5OutputCurrentMaxThirteen OBJECT-TYPE
    SYNTAX      DisplayString
    MAX-ACCESS  read-write
    STATUS      current
    DESCRIPTION
	"The second output Max. current alarm value of slave5"
    ::= { slave5OutputCurrentMax 13}

slave5OutputCurrentMaxFourteen OBJECT-TYPE
    SYNTAX      DisplayString
    MAX-ACCESS  read-write
    STATUS      current
    DESCRIPTION
	"The second output Max. current alarm value of slave5"
    ::= { slave5OutputCurrentMax 14}

slave5OutputCurrentMaxFifteen OBJECT-TYPE
    SYNTAX      DisplayString
    MAX-ACCESS  read-write
    STATUS      current
    DESCRIPTION
	"The second output Max. current alarm value of slave5"
    ::= { slave5OutputCurrentMax 15}

slave5OutputCurrentMaxSixteen OBJECT-TYPE
    SYNTAX      DisplayString
    MAX-ACCESS  read-write
    STATUS      current
    DESCRIPTION
	"The second output Max. current alarm value of slave5"
    ::= { slave5OutputCurrentMax 16}

slave5OutputCurrentMaxSeventeen OBJECT-TYPE
    SYNTAX      DisplayString
    MAX-ACCESS  read-write
    STATUS      current
    DESCRIPTION
	"The second output Max. current alarm value of slave5"
    ::= { slave5OutputCurrentMax 17}

slave5OutputCurrentMaxEighteen OBJECT-TYPE
    SYNTAX      DisplayString
    MAX-ACCESS  read-write
    STATUS      current
    DESCRIPTION
	"The second output Max. current alarm value of slave5"
    ::= { slave5OutputCurrentMax 18}
	
slave5OutputCurrentMaxNineteen OBJECT-TYPE
    SYNTAX      DisplayString
    MAX-ACCESS  read-write
    STATUS      current
    DESCRIPTION
	"The second output Max. current alarm value of slave5"
    ::= { slave5OutputCurrentMax 19}
	
slave5OutputCurrentMaxtwenty OBJECT-TYPE
    SYNTAX      DisplayString
    MAX-ACCESS  read-write
    STATUS      current
    DESCRIPTION
	"The second output Max. current alarm value of slave5"
    ::= { slave5OutputCurrentMax 20}
	
slave5OutputCurrentMaxTwentyone OBJECT-TYPE
    SYNTAX      DisplayString
    MAX-ACCESS  read-write
    STATUS      current
    DESCRIPTION
	"The second output Max. current alarm value of slave5"
    ::= { slave5OutputCurrentMax 21}
	
slave5OutputCurrentMaxTwentyonetwo OBJECT-TYPE
    SYNTAX      DisplayString
    MAX-ACCESS  read-write
    STATUS      current
    DESCRIPTION
	"The second output Max. current alarm value of slave5"
    ::= { slave5OutputCurrentMax 22}
	
slave5OutputCurrentMaxTwentythree OBJECT-TYPE
    SYNTAX      DisplayString
    MAX-ACCESS  read-write
    STATUS      current
    DESCRIPTION
	"The second output Max. current alarm value of slave5"
    ::= { slave5OutputCurrentMax 23}
	
slave5OutputCurrentMaxTwentyfour OBJECT-TYPE
    SYNTAX      DisplayString
    MAX-ACCESS  read-write
    STATUS      current
    DESCRIPTION
	"The second output Max. current alarm value of slave5"
    ::= { slave5OutputCurrentMax 24}
	
slave5OutputCurrentMaxTwentyfive OBJECT-TYPE
    SYNTAX      DisplayString
    MAX-ACCESS  read-write
    STATUS      current
    DESCRIPTION
	"The second output Max. current alarm value of slave5"
    ::= { slave5OutputCurrentMax 25}
	
slave5OutputCurrentMaxTwentysix OBJECT-TYPE
    SYNTAX      DisplayString
    MAX-ACCESS  read-write
    STATUS      current
    DESCRIPTION
	"The second output Max. current alarm value of slave5"
    ::= { slave5OutputCurrentMax 26}
	
slave5OutputCurrentMaxTwentyseven OBJECT-TYPE
    SYNTAX      DisplayString
    MAX-ACCESS  read-write
    STATUS      current
    DESCRIPTION
	"The second output Max. current alarm value of slave5"
    ::= { slave5OutputCurrentMax 27}
	
slave5OutputCurrentMaxTwentyeight OBJECT-TYPE
    SYNTAX      DisplayString
    MAX-ACCESS  read-write
    STATUS      current
    DESCRIPTION
	"The second output Max. current alarm value of slave5"
    ::= { slave5OutputCurrentMax 28}	
slave5OutputCurrentMaxTwentynine OBJECT-TYPE
    SYNTAX      DisplayString
    MAX-ACCESS  read-write
    STATUS      current
    DESCRIPTION
	"The second output Max. current alarm value of slave5"
    ::= { slave5OutputCurrentMax 29}
	
slave5OutputCurrentMaxThirty OBJECT-TYPE
    SYNTAX      DisplayString
    MAX-ACCESS  read-write
    STATUS      current
    DESCRIPTION
	"The second output Max. current alarm value of slave5"
    ::= { slave5OutputCurrentMax 30}
	
slave5OutputCurrentMaxThirtyone OBJECT-TYPE
    SYNTAX      DisplayString
    MAX-ACCESS  read-write
    STATUS      current
    DESCRIPTION
	"The second output Max. current alarm value of slave5"
    ::= { slave5OutputCurrentMax 31}
	
slave5OutputCurrentMaxThirtytwo OBJECT-TYPE
    SYNTAX      DisplayString
    MAX-ACCESS  read-write
    STATUS      current
    DESCRIPTION
	"The second output Max. current alarm value of slave5"
    ::= { slave5OutputCurrentMax 32}
	
slave5OutputCurrentMaxThirtythree OBJECT-TYPE
    SYNTAX      DisplayString
    MAX-ACCESS  read-write
    STATUS      current
    DESCRIPTION
	"The second output Max. current alarm value of slave5"
    ::= { slave5OutputCurrentMax 33}
	
slave5OutputCurrentMaxThirtyfour OBJECT-TYPE
    SYNTAX      DisplayString
    MAX-ACCESS  read-write
    STATUS      current
    DESCRIPTION
	"The second output Max. current alarm value of slave5"
    ::= { slave5OutputCurrentMax 34}
	
slave5OutputCurrentMaxThirtyfive OBJECT-TYPE
    SYNTAX      DisplayString
    MAX-ACCESS  read-write
    STATUS      current
    DESCRIPTION
	"The second output Max. current alarm value of slave5"
    ::= { slave5OutputCurrentMax 35}
	
slave5OutputCurrentMaxThirtysix OBJECT-TYPE
    SYNTAX      DisplayString
    MAX-ACCESS  read-write
    STATUS      current
    DESCRIPTION
	"The second output Max. current alarm value of slave5"
    ::= { slave5OutputCurrentMax 36}
	
slave5OutputCurrentMaxThirtyseven OBJECT-TYPE
    SYNTAX      DisplayString
    MAX-ACCESS  read-write
    STATUS      current
    DESCRIPTION
	"The second output Max. current alarm value of slave5"
    ::= { slave5OutputCurrentMax 37}
	
slave5OutputCurrentMaxThirtyeight OBJECT-TYPE
    SYNTAX      DisplayString
    MAX-ACCESS  read-write
    STATUS      current
    DESCRIPTION
	"The second output Max. current alarm value of slave5"
    ::= { slave5OutputCurrentMax 38}
	
slave5OutputCurrentMaxThirtynine OBJECT-TYPE
    SYNTAX      DisplayString
    MAX-ACCESS  read-write
    STATUS      current
    DESCRIPTION
	"The second output Max. current alarm value of slave5"
    ::= { slave5OutputCurrentMax 39}
	
slave5OutputCurrentMaxFourty OBJECT-TYPE
    SYNTAX      DisplayString
    MAX-ACCESS  read-write
    STATUS      current
    DESCRIPTION
	"The second output Max. current alarm value of slave5"
    ::= { slave5OutputCurrentMax 40}
	
slave5OutputCurrentMaxFourtyone OBJECT-TYPE
    SYNTAX      DisplayString
    MAX-ACCESS  read-write
    STATUS      current
    DESCRIPTION
	"The second output Max. current alarm value of slave5"
    ::= { slave5OutputCurrentMax 41}
	
slave5OutputCurrentMaxFourtytwo OBJECT-TYPE
    SYNTAX      DisplayString
    MAX-ACCESS  read-write
    STATUS      current
    DESCRIPTION
	"The second output Max. current alarm value of slave5"
    ::= { slave5OutputCurrentMax 42}
	
	
-------------------------------slave5 output powerfactor------------------------	
slave5OutputPowerfactor OBJECT IDENTIFIER ::= { slave5 9}	

slave5OutputPowerfactorOne OBJECT-TYPE
    SYNTAX      DisplayString
    MAX-ACCESS  read-only
    STATUS      current
    DESCRIPTION
	"The ouput power factor of slave5." 
	::= { slave5OutputPowerfactor 1}

slave5OutputPowerfactorTwo OBJECT-TYPE
    SYNTAX      DisplayString
    MAX-ACCESS  read-only
    STATUS      current
    DESCRIPTION
	"The ouput power factor of slave5." 
	::= { slave5OutputPowerfactor 2}
	
slave5OutputPowerfactorThree OBJECT-TYPE
    SYNTAX      DisplayString
    MAX-ACCESS  read-only
    STATUS      current
    DESCRIPTION
	"The ouput power factor of slave5." 
	::= { slave5OutputPowerfactor 3}
	
slave5OutputPowerfactorFour OBJECT-TYPE
    SYNTAX      DisplayString
    MAX-ACCESS  read-only
    STATUS      current
    DESCRIPTION
	"The ouput power factor of slave5." 
	::= { slave5OutputPowerfactor 4}
		
slave5OutputPowerfactorFive OBJECT-TYPE
    SYNTAX      DisplayString
    MAX-ACCESS  read-only
    STATUS      current
    DESCRIPTION
	"The ouput power factor of slave5." 
	::= { slave5OutputPowerfactor 5}
	
slave5OutputPowerfactorSix OBJECT-TYPE
    SYNTAX      DisplayString
    MAX-ACCESS  read-only
    STATUS      current
    DESCRIPTION
	"The ouput power factor of slave5." 
	::= { slave5OutputPowerfactor 6}
	
slave5OutputPowerfactorSeven OBJECT-TYPE
    SYNTAX      DisplayString
    MAX-ACCESS  read-only
    STATUS      current
    DESCRIPTION
	"The ouput power factor of slave5." 
	::= { slave5OutputPowerfactor 7}	
	
slave5OutputPowerfactorEight OBJECT-TYPE
    SYNTAX      DisplayString
    MAX-ACCESS  read-only
    STATUS      current
    DESCRIPTION
	"The ouput power factor of slave5." 
	::= { slave5OutputPowerfactor 8}
	
slave5OutputPowerfactorNine OBJECT-TYPE
    SYNTAX      DisplayString
    MAX-ACCESS  read-only
    STATUS      current
    DESCRIPTION
	"The ouput power factor of slave5." 
	::= { slave5OutputPowerfactor 9}
		
slave5OutputPowerfactorTen OBJECT-TYPE
    SYNTAX      DisplayString
    MAX-ACCESS  read-only
    STATUS      current
    DESCRIPTION
	"The ouput power factor of slave5." 
	::= { slave5OutputPowerfactor 10}
		
slave5OutputPowerfactorEleven OBJECT-TYPE
    SYNTAX      DisplayString
    MAX-ACCESS  read-only
    STATUS      current
    DESCRIPTION
	"The ouput power factor of slave5." 
	::= { slave5OutputPowerfactor 11}
		
slave5OutputPowerfactorTwel OBJECT-TYPE
    SYNTAX      DisplayString
    MAX-ACCESS  read-only
    STATUS      current
    DESCRIPTION
	"The ouput power factor of slave5." 
	::= { slave5OutputPowerfactor 12}
		
slave5OutputPowerfactorThirteen OBJECT-TYPE
    SYNTAX      DisplayString
    MAX-ACCESS  read-only
    STATUS      current
    DESCRIPTION
	"The ouput power factor of slave5." 
	::= { slave5OutputPowerfactor 13}
		
slave5OutputPowerfactorFourteen OBJECT-TYPE
    SYNTAX      DisplayString
    MAX-ACCESS  read-only
    STATUS      current
    DESCRIPTION
	"The ouput power factor of slave5." 
	::= { slave5OutputPowerfactor 14}
		
slave5OutputPowerfactorFifteen OBJECT-TYPE
    SYNTAX      DisplayString
    MAX-ACCESS  read-only
    STATUS      current
    DESCRIPTION
	"The ouput power factor of slave5." 
	::= { slave5OutputPowerfactor 15}
		
slave5OutputPowerfactorSixteen OBJECT-TYPE
    SYNTAX      DisplayString
    MAX-ACCESS  read-only
    STATUS      current
    DESCRIPTION
	"The ouput power factor of slave5." 
	::= { slave5OutputPowerfactor 16}
		
slave5OutputPowerfactorSeventeen OBJECT-TYPE
    SYNTAX      DisplayString
    MAX-ACCESS  read-only
    STATUS      current
    DESCRIPTION
	"The ouput power factor of slave5." 
	::= { slave5OutputPowerfactor 17}
		
slave5OutputPowerfactorEighteen OBJECT-TYPE
    SYNTAX      DisplayString
    MAX-ACCESS  read-only
    STATUS      current
    DESCRIPTION
	"The ouput power factor of slave5." 
	::= { slave5OutputPowerfactor 18}
		
slave5OutputPowerfactorNineteen OBJECT-TYPE
    SYNTAX      DisplayString
    MAX-ACCESS  read-only
    STATUS      current
    DESCRIPTION
	"The ouput power factor of slave5." 
	::= { slave5OutputPowerfactor 19}
		
slave5OutputPowerfactorTwenty OBJECT-TYPE
    SYNTAX      DisplayString
    MAX-ACCESS  read-only
    STATUS      current
    DESCRIPTION
	"The ouput power factor of slave5." 
	::= { slave5OutputPowerfactor 20}
		
slave5OutputPowerfactorTwentyone OBJECT-TYPE
    SYNTAX      DisplayString
    MAX-ACCESS  read-only
    STATUS      current
    DESCRIPTION
	"The ouput power factor of slave5." 
	::= { slave5OutputPowerfactor 21}
		
slave5OutputPowerfactorTwentytwo OBJECT-TYPE
    SYNTAX      DisplayString
    MAX-ACCESS  read-only
    STATUS      current
    DESCRIPTION
	"The ouput power factor of slave5." 
	::= { slave5OutputPowerfactor 22}
		
slave5OutputPowerfactorTwentythree OBJECT-TYPE
    SYNTAX      DisplayString
    MAX-ACCESS  read-only
    STATUS      current
    DESCRIPTION
	"The ouput power factor of slave5." 
	::= { slave5OutputPowerfactor 23}
		
slave5OutputPowerfactorTwentyfour OBJECT-TYPE
    SYNTAX      DisplayString
    MAX-ACCESS  read-only
    STATUS      current
    DESCRIPTION
	"The ouput power factor of slave5." 
	::= { slave5OutputPowerfactor 24}
		
slave5OutputPowerfactorTwentyfive OBJECT-TYPE
    SYNTAX      DisplayString
    MAX-ACCESS  read-only
    STATUS      current
    DESCRIPTION
	"The ouput power factor of slave5." 
	::= { slave5OutputPowerfactor 25}
		
slave5OutputPowerfactorTwentysix OBJECT-TYPE
    SYNTAX      DisplayString
    MAX-ACCESS  read-only
    STATUS      current
    DESCRIPTION
	"The ouput power factor of slave5." 
	::= { slave5OutputPowerfactor 26}
		
slave5OutputPowerfactorTwentyseven OBJECT-TYPE
    SYNTAX      DisplayString
    MAX-ACCESS  read-only
    STATUS      current
    DESCRIPTION
	"The ouput power factor of slave5." 
	::= { slave5OutputPowerfactor 27}
		
slave5OutputPowerfactorTwentyeight OBJECT-TYPE
    SYNTAX      DisplayString
    MAX-ACCESS  read-only
    STATUS      current
    DESCRIPTION
	"The ouput power factor of slave5." 
	::= { slave5OutputPowerfactor 28}
		
slave5OutputPowerfactorTwentynine OBJECT-TYPE
    SYNTAX      DisplayString
    MAX-ACCESS  read-only
    STATUS      current
    DESCRIPTION
	"The ouput power factor of slave5." 
	::= { slave5OutputPowerfactor 29}
		
slave5OutputPowerfactorThirty OBJECT-TYPE
    SYNTAX      DisplayString
    MAX-ACCESS  read-only
    STATUS      current
    DESCRIPTION
	"The ouput power factor of slave5." 
	::= { slave5OutputPowerfactor 30}
		
slave5OutputPowerfactorThirtyone OBJECT-TYPE
    SYNTAX      DisplayString
    MAX-ACCESS  read-only
    STATUS      current
    DESCRIPTION
	"The ouput power factor of slave5." 
	::= { slave5OutputPowerfactor 31}
		
slave5OutputPowerfactorThirtytwo OBJECT-TYPE
    SYNTAX      DisplayString
    MAX-ACCESS  read-only
    STATUS      current
    DESCRIPTION
	"The ouput power factor of slave5." 
	::= { slave5OutputPowerfactor 32}
		
slave5OutputPowerfactorThirtythree OBJECT-TYPE
    SYNTAX      DisplayString
    MAX-ACCESS  read-only
    STATUS      current
    DESCRIPTION
	"The ouput power factor of slave5." 
	::= { slave5OutputPowerfactor 33}	
	
slave5OutputPowerfactorThirtyfour OBJECT-TYPE
    SYNTAX      DisplayString
    MAX-ACCESS  read-only
    STATUS      current
    DESCRIPTION
	"The ouput power factor of slave5." 
	::= { slave5OutputPowerfactor 34}
	
	
slave5OutputPowerfactorThirtyfive OBJECT-TYPE
    SYNTAX      DisplayString
    MAX-ACCESS  read-only
    STATUS      current
    DESCRIPTION
	"The ouput power factor of slave5." 
	::= { slave5OutputPowerfactor 35}
		
slave5OutputPowerfactorThirtysix OBJECT-TYPE
    SYNTAX      DisplayString
    MAX-ACCESS  read-only
    STATUS      current
    DESCRIPTION
	"The ouput power factor of slave5." 
	::= { slave5OutputPowerfactor 36}
		
slave5OutputPowerfactorThirtyseven OBJECT-TYPE
    SYNTAX      DisplayString
    MAX-ACCESS  read-only
    STATUS      current
    DESCRIPTION
	"The ouput power factor of slave5." 
	::= { slave5OutputPowerfactor 37}
		
slave5OutputPowerfactorThirtyeight OBJECT-TYPE
    SYNTAX      DisplayString
    MAX-ACCESS  read-only
    STATUS      current
    DESCRIPTION
	"The ouput power factor of slave5." 
	::= { slave5OutputPowerfactor 38}
		
slave5OutputPowerfactorThirtynine OBJECT-TYPE
    SYNTAX      DisplayString
    MAX-ACCESS  read-only
    STATUS      current
    DESCRIPTION
	"The ouput power factor of slave5." 
	::= { slave5OutputPowerfactor 39}
		
slave5OutputPowerfactorFourty OBJECT-TYPE
    SYNTAX      DisplayString
    MAX-ACCESS  read-only
    STATUS      current
    DESCRIPTION
	"The ouput power factor of slave5." 
	::= { slave5OutputPowerfactor 40}
		
slave5OutputPowerfactorFourtyone OBJECT-TYPE
    SYNTAX      DisplayString
    MAX-ACCESS  read-only
    STATUS      current
    DESCRIPTION
	"The ouput power factor of slave5." 
	::= { slave5OutputPowerfactor 41}
		
slave5OutputPowerfactorFourtytwo OBJECT-TYPE
    SYNTAX      DisplayString
    MAX-ACCESS  read-only
    STATUS      current
    DESCRIPTION
	"The ouput power factor of slave5." 
	::= { slave5OutputPowerfactor 42}	
	
-------------------------------slave5 output energy------------------------	
slave5OutputEnergy OBJECT IDENTIFIER ::= { slave5 10}

slave5OutputEnergyOne OBJECT-TYPE
    SYNTAX      DisplayString
    MAX-ACCESS  read-only
    STATUS      current
    DESCRIPTION
	"The ouput power of slave5." 
	::= { slave5OutputEnergy 1}

slave5OutputEnergyTwo OBJECT-TYPE
    SYNTAX      DisplayString
    MAX-ACCESS  read-only
    STATUS      current
    DESCRIPTION
	"The ouput power of slave5." 
	::= { slave5OutputEnergy 2}
	
slave5OutputEnergyThree OBJECT-TYPE
    SYNTAX      DisplayString
    MAX-ACCESS  read-only
    STATUS      current
    DESCRIPTION
	"The ouput power of slave5." 
	::= { slave5OutputEnergy 3}
	
slave5OutputEnergyFour OBJECT-TYPE
    SYNTAX      DisplayString
    MAX-ACCESS  read-only
    STATUS      current
    DESCRIPTION
	"The ouput power of slave5." 
	::= { slave5OutputEnergy 4}
		
slave5OutputEnergyFive OBJECT-TYPE
    SYNTAX      DisplayString
    MAX-ACCESS  read-only
    STATUS      current
    DESCRIPTION
	"The ouput power of slave5." 
	::= { slave5OutputEnergy 5}
	
slave5OutputEnergySix OBJECT-TYPE
    SYNTAX      DisplayString
    MAX-ACCESS  read-only
    STATUS      current
    DESCRIPTION
	"The ouput power of slave5." 
	::= { slave5OutputEnergy 6}
	
slave5OutputEnergySeven OBJECT-TYPE
    SYNTAX      DisplayString
    MAX-ACCESS  read-only
    STATUS      current
    DESCRIPTION
	"The ouput power of slave5." 
	::= { slave5OutputEnergy 7}	
	
slave5OutputEnergyEight OBJECT-TYPE
    SYNTAX      DisplayString
    MAX-ACCESS  read-only
    STATUS      current
    DESCRIPTION
	"The ouput power of slave5." 
	::= { slave5OutputEnergy 8}
	
slave5OutputEnergyNine OBJECT-TYPE
    SYNTAX      DisplayString
    MAX-ACCESS  read-only
    STATUS      current
    DESCRIPTION
	"The ouput power of slave5." 
	::= { slave5OutputEnergy 9}
		
slave5OutputEnergyTen OBJECT-TYPE
    SYNTAX      DisplayString
    MAX-ACCESS  read-only
    STATUS      current
    DESCRIPTION
	"The ouput power of slave5." 
	::= { slave5OutputEnergy 10}
		
slave5OutputEnergyEleven OBJECT-TYPE
    SYNTAX      DisplayString
    MAX-ACCESS  read-only
    STATUS      current
    DESCRIPTION
	"The ouput power of slave5." 
	::= { slave5OutputEnergy 11}
		
slave5OutputEnergyTwel OBJECT-TYPE
    SYNTAX      DisplayString
    MAX-ACCESS  read-only
    STATUS      current
    DESCRIPTION
	"The ouput power of slave5." 
	::= { slave5OutputEnergy 12}
		
slave5OutputEnergyThirteen OBJECT-TYPE
    SYNTAX      DisplayString
    MAX-ACCESS  read-only
    STATUS      current
    DESCRIPTION
	"The ouput power of slave5." 
	::= { slave5OutputEnergy 13}
		
slave5OutputEnergyFourteen OBJECT-TYPE
    SYNTAX      DisplayString
    MAX-ACCESS  read-only
    STATUS      current
    DESCRIPTION
	"The ouput power of slave5." 
	::= { slave5OutputEnergy 14}
		
slave5OutputEnergyFifteen OBJECT-TYPE
    SYNTAX      DisplayString
    MAX-ACCESS  read-only
    STATUS      current
    DESCRIPTION
	"The ouput power of slave5." 
	::= { slave5OutputEnergy 15}
		
slave5OutputEnergySixteen OBJECT-TYPE
    SYNTAX      DisplayString
    MAX-ACCESS  read-only
    STATUS      current
    DESCRIPTION
	"The ouput power of slave5." 
	::= { slave5OutputEnergy 16}
		
slave5OutputEnergySeventeen OBJECT-TYPE
    SYNTAX      DisplayString
    MAX-ACCESS  read-only
    STATUS      current
    DESCRIPTION
	"The ouput power of slave5." 
	::= { slave5OutputEnergy 17}
		
slave5OutputEnergyEighteen OBJECT-TYPE
    SYNTAX      DisplayString
    MAX-ACCESS  read-only
    STATUS      current
    DESCRIPTION
	"The ouput power of slave5." 
	::= { slave5OutputEnergy 18}
		
slave5OutputEnergyNineteen OBJECT-TYPE
    SYNTAX      DisplayString
    MAX-ACCESS  read-only
    STATUS      current
    DESCRIPTION
	"The ouput power of slave5." 
	::= { slave5OutputEnergy 19}
		
slave5OutputEnergyTwenty OBJECT-TYPE
    SYNTAX      DisplayString
    MAX-ACCESS  read-only
    STATUS      current
    DESCRIPTION
	"The ouput power of slave5." 
	::= { slave5OutputEnergy 20}
		
slave5OutputEnergyTwentyone OBJECT-TYPE
    SYNTAX      DisplayString
    MAX-ACCESS  read-only
    STATUS      current
    DESCRIPTION
	"The ouput power of slave5." 
	::= { slave5OutputEnergy 21}
		
slave5OutputEnergyTwentytwo OBJECT-TYPE
    SYNTAX      DisplayString
    MAX-ACCESS  read-only
    STATUS      current
    DESCRIPTION
	"The ouput power of slave5." 
	::= { slave5OutputEnergy 22}
		
slave5OutputEnergyTwentythree OBJECT-TYPE
    SYNTAX      DisplayString
    MAX-ACCESS  read-only
    STATUS      current
    DESCRIPTION
	"The ouput power of slave5." 
	::= { slave5OutputEnergy 23}
		
slave5OutputEnergyTwentyfour OBJECT-TYPE
    SYNTAX      DisplayString
    MAX-ACCESS  read-only
    STATUS      current
    DESCRIPTION
	"The ouput power of slave5." 
	::= { slave5OutputEnergy 24}
		
slave5OutputEnergyTwentyfive OBJECT-TYPE
    SYNTAX      DisplayString
    MAX-ACCESS  read-only
    STATUS      current
    DESCRIPTION
	"The ouput power of slave5." 
	::= { slave5OutputEnergy 25}
		
slave5OutputEnergyTwentysix OBJECT-TYPE
    SYNTAX      DisplayString
    MAX-ACCESS  read-only
    STATUS      current
    DESCRIPTION
	"The ouput power of slave5." 
	::= { slave5OutputEnergy 26}
		
slave5OutputEnergyTwentyseven OBJECT-TYPE
    SYNTAX      DisplayString
    MAX-ACCESS  read-only
    STATUS      current
    DESCRIPTION
	"The ouput power of slave5." 
	::= { slave5OutputEnergy 27}
		
slave5OutputEnergyTwentyeight OBJECT-TYPE
    SYNTAX      DisplayString
    MAX-ACCESS  read-only
    STATUS      current
    DESCRIPTION
	"The ouput power of slave5." 
	::= { slave5OutputEnergy 28}
		
slave5OutputEnergyTwentynine OBJECT-TYPE
    SYNTAX      DisplayString
    MAX-ACCESS  read-only
    STATUS      current
    DESCRIPTION
	"The ouput power of slave5." 
	::= { slave5OutputEnergy 29}
		
slave5OutputEnergyThirty OBJECT-TYPE
    SYNTAX      DisplayString
    MAX-ACCESS  read-only
    STATUS      current
    DESCRIPTION
	"The ouput power of slave5." 
	::= { slave5OutputEnergy 30}
		
slave5OutputEnergyThirtyone OBJECT-TYPE
    SYNTAX      DisplayString
    MAX-ACCESS  read-only
    STATUS      current
    DESCRIPTION
	"The ouput power of slave5." 
	::= { slave5OutputEnergy 31}
		
slave5OutputEnergyThirtytwo OBJECT-TYPE
    SYNTAX      DisplayString
    MAX-ACCESS  read-only
    STATUS      current
    DESCRIPTION
	"The ouput power of slave5." 
	::= { slave5OutputEnergy 32}
		
slave5OutputEnergyThirtythree OBJECT-TYPE
    SYNTAX      DisplayString
    MAX-ACCESS  read-only
    STATUS      current
    DESCRIPTION
	"The ouput power of slave5." 
	::= { slave5OutputEnergy 33}	
	
slave5OutputEnergyThirtyfour OBJECT-TYPE
    SYNTAX      DisplayString
    MAX-ACCESS  read-only
    STATUS      current
    DESCRIPTION
	"The ouput power of slave5." 
	::= { slave5OutputEnergy 34}
	
	
slave5OutputEnergyThirtyfive OBJECT-TYPE
    SYNTAX      DisplayString
    MAX-ACCESS  read-only
    STATUS      current
    DESCRIPTION
	"The ouput power of slave5." 
	::= { slave5OutputEnergy 35}
		
slave5OutputEnergyThirtysix OBJECT-TYPE
    SYNTAX      DisplayString
    MAX-ACCESS  read-only
    STATUS      current
    DESCRIPTION
	"The ouput power of slave5." 
	::= { slave5OutputEnergy 36}
		
slave5OutputEnergyThirtyseven OBJECT-TYPE
    SYNTAX      DisplayString
    MAX-ACCESS  read-only
    STATUS      current
    DESCRIPTION
	"The ouput power of slave5." 
	::= { slave5OutputEnergy 37}
		
slave5OutputEnergyThirtyeight OBJECT-TYPE
    SYNTAX      DisplayString
    MAX-ACCESS  read-only
    STATUS      current
    DESCRIPTION
	"The ouput power of slave5." 
	::= { slave5OutputEnergy 38}
		
slave5OutputEnergyThirtynine OBJECT-TYPE
    SYNTAX      DisplayString
    MAX-ACCESS  read-only
    STATUS      current
    DESCRIPTION
	"The ouput power of slave5." 
	::= { slave5OutputEnergy 39}
		
slave5OutputEnergyFourty OBJECT-TYPE
    SYNTAX      DisplayString
    MAX-ACCESS  read-only
    STATUS      current
    DESCRIPTION
	"The ouput power of slave5." 
	::= { slave5OutputEnergy 40}
		
slave5OutputEnergyFourtyone OBJECT-TYPE
    SYNTAX      DisplayString
    MAX-ACCESS  read-only
    STATUS      current
    DESCRIPTION
	"The ouput power of slave5." 
	::= { slave5OutputEnergy 41}
		
slave5OutputEnergyFourtytwo OBJECT-TYPE
    SYNTAX      DisplayString
    MAX-ACCESS  read-only
    STATUS      current
    DESCRIPTION
	"The ouput power of slave5." 
	::= { slave5OutputEnergy 42}	
	




-------------------------------slave6 information--------------------
slave6 OBJECT IDENTIFIER ::= { pdu 7}
slave6Information OBJECT IDENTIFIER ::= { slave6 1}
slave6Name OBJECT-TYPE
    SYNTAX      DisplayString
    MAX-ACCESS  read-write
    STATUS      current
    DESCRIPTION
	"This is the first device."
    ::= { slave6Information 1}
    
slave6Type OBJECT-TYPE
    SYNTAX      DisplayString
    MAX-ACCESS  read-only
    STATUS      current
    DESCRIPTION
	"This is device type "
    ::= { slave6Information 2}
    
slave6OutputNumber OBJECT-TYPE 
    SYNTAX      Integer32
    MAX-ACCESS  read-only
    STATUS      current
    DESCRIPTION
	"This is the number of output bits"
	::= { slave6Information 3}
	
slave6MacAdress OBJECT-TYPE
    SYNTAX      DisplayString
    MAX-ACCESS  read-only
    STATUS      current
    DESCRIPTION
	"This is device MAC adress"
    ::= { slave6Information 4}	

slave6Vison OBJECT-TYPE
    SYNTAX      DisplayString
    MAX-ACCESS  read-only
    STATUS      current
    DESCRIPTION
	"This is device vison "
    ::= { slave6Information 5}

slave6Frequency OBJECT-TYPE
    SYNTAX      Integer32
    MAX-ACCESS  read-only
    STATUS      current
    DESCRIPTION
	"This is device frequency "
    ::= { slave6Information 6}
	
slave6Emission OBJECT-TYPE
    SYNTAX      DisplayString
    MAX-ACCESS  read-only
    STATUS      current
    DESCRIPTION
	"This is device emission "
    ::= { slave6Information 7}	
	
slave6RunTime OBJECT-TYPE
    SYNTAX      DisplayString
    MAX-ACCESS  read-only
    STATUS      current
    DESCRIPTION
	"This is device running time "
    ::= { slave6Information 8}	

slave6BuzzerSwitch OBJECT-TYPE
    SYNTAX      DisplayString
    MAX-ACCESS  read-write
    STATUS      current
    DESCRIPTION
	"This is device buzzer switch."
    ::= { slave6Information 9}	

	
-------------------------------slave6 phase--------------------
slave6Phase OBJECT IDENTIFIER ::= { slave6 2}	
	
slave6PhaseOne OBJECT IDENTIFIER ::= { slave6Phase 1}	    
slave6PhaseOneCurrent OBJECT-TYPE
    SYNTAX      DisplayString
    MAX-ACCESS  read-only
    STATUS      current
    DESCRIPTION
	"The power of phase one"
    ::= { slave6PhaseOne 1}

slave6PhaseOneVoltage OBJECT-TYPE
    SYNTAX      DisplayString
    MAX-ACCESS  read-only
    STATUS      current
    DESCRIPTION
	"The power of phase one"
    ::= { slave6PhaseOne 2}

slave6PhaseOnePower OBJECT-TYPE
    SYNTAX      DisplayString
    MAX-ACCESS  read-only
    STATUS      current
    DESCRIPTION
	"The power of phase one"
    ::= { slave6PhaseOne 3}
	
slave6PhaseOnePowerfactor OBJECT-TYPE
    SYNTAX      DisplayString
    MAX-ACCESS  read-only
    STATUS      current
    DESCRIPTION
	"The power of phase one"
    ::= { slave6PhaseOne 4}	
	
slave6PhaseOneEnergy OBJECT-TYPE
    SYNTAX      DisplayString
    MAX-ACCESS  read-only
    STATUS      current
    DESCRIPTION
	"The power of phase one"
    ::= { slave6PhaseOne 5}	
		
slave6PhaseOneCurrentMin OBJECT-TYPE
    SYNTAX      DisplayString
    MAX-ACCESS  read-write
    STATUS      current
    DESCRIPTION
	"The power of phase one"
    ::= { slave6PhaseOne 6}	
	
slave6PhaseOneCurrentMinCritical OBJECT-TYPE
    SYNTAX      DisplayString
    MAX-ACCESS  read-write
    STATUS      current
    DESCRIPTION
	"The power of phase one"
    ::= { slave6PhaseOne 7}
	
slave6PhaseOneCurrentMaxCritical OBJECT-TYPE
    SYNTAX      DisplayString
    MAX-ACCESS  read-write
    STATUS      current
    DESCRIPTION
	"The power of phase one"
    ::= { slave6PhaseOne 8}
	
slave6PhaseOneCurrentMax OBJECT-TYPE
    SYNTAX      DisplayString
    MAX-ACCESS  read-write
    STATUS      current
    DESCRIPTION
	"The power of phase one"
    ::= { slave6PhaseOne 9}
	
slave6PhaseOneVoltageMin OBJECT-TYPE
    SYNTAX      DisplayString
    MAX-ACCESS  read-write
    STATUS      current
    DESCRIPTION
	"The power of phase one"
    ::= { slave6PhaseOne 10}
	
slave6PhaseOneVoltageMinCritical OBJECT-TYPE
    SYNTAX      DisplayString
    MAX-ACCESS  read-write
    STATUS      current
    DESCRIPTION
	"The power of phase one"
    ::= { slave6PhaseOne 11}

slave6PhaseOneVoltageMaxCritical OBJECT-TYPE
    SYNTAX      DisplayString
    MAX-ACCESS  read-write
    STATUS      current
    DESCRIPTION
	"The power of phase one"
    ::= { slave6PhaseOne 12}
	
slave6PhaseOneVoltageMax OBJECT-TYPE
    SYNTAX      DisplayString
    MAX-ACCESS  read-write
    STATUS      current
    DESCRIPTION
	"The power of phase one"
    ::= { slave6PhaseOne 13}


slave6PhaseTwo OBJECT IDENTIFIER ::= { slave6Phase 2}	    
slave6PhaseTwoCurrent OBJECT-TYPE
    SYNTAX      DisplayString
    MAX-ACCESS  read-only
    STATUS      current
    DESCRIPTION
	"The power of phase one"
    ::= { slave6PhaseTwo 1}

slave6PhaseTwoVoltage OBJECT-TYPE
    SYNTAX      DisplayString
    MAX-ACCESS  read-only
    STATUS      current
    DESCRIPTION
	"The power of phase one"
    ::= { slave6PhaseTwo 2}

slave6PhaseTwoPower OBJECT-TYPE
    SYNTAX      DisplayString
    MAX-ACCESS  read-only
    STATUS      current
    DESCRIPTION
	"The power of phase one"
    ::= { slave6PhaseTwo 3}
	
slave6PhaseTwoPowerfactor OBJECT-TYPE
    SYNTAX      DisplayString
    MAX-ACCESS  read-only
    STATUS      current
    DESCRIPTION
	"The power of phase one"
    ::= { slave6PhaseTwo 4}	
	
slave6PhaseTwoEnergy OBJECT-TYPE
    SYNTAX      DisplayString
    MAX-ACCESS  read-only
    STATUS      current
    DESCRIPTION
	"The power of phase one"
    ::= { slave6PhaseTwo 5}	
		
slave6PhaseTwoCurrentMin OBJECT-TYPE
    SYNTAX      DisplayString
    MAX-ACCESS  read-write
    STATUS      current
    DESCRIPTION
	"The power of phase one"
    ::= { slave6PhaseTwo 6}	
	
slave6PhaseTwoCurrentMinCritical OBJECT-TYPE
    SYNTAX      DisplayString
    MAX-ACCESS  read-write
    STATUS      current
    DESCRIPTION
	"The power of phase one"
    ::= { slave6PhaseTwo 7}
	
slave6PhaseTwoCurrentMaxCritical OBJECT-TYPE
    SYNTAX      DisplayString
    MAX-ACCESS  read-write
    STATUS      current
    DESCRIPTION
	"The power of phase one"
    ::= { slave6PhaseTwo 8}
	
slave6PhaseTwoCurrentMax OBJECT-TYPE
    SYNTAX      DisplayString
    MAX-ACCESS  read-write
    STATUS      current
    DESCRIPTION
	"The power of phase one"
    ::= { slave6PhaseTwo 9}
	
slave6PhaseTwoVoltageMin OBJECT-TYPE
    SYNTAX      DisplayString
    MAX-ACCESS  read-write
    STATUS      current
    DESCRIPTION
	"The power of phase one"
    ::= { slave6PhaseTwo 10}
	
slave6PhaseTwoVoltageMinCritical OBJECT-TYPE
    SYNTAX      DisplayString
    MAX-ACCESS  read-write
    STATUS      current
    DESCRIPTION
	"The power of phase one"
    ::= { slave6PhaseTwo 11}

slave6PhaseTwoVoltageMaxCritical OBJECT-TYPE
    SYNTAX      DisplayString
    MAX-ACCESS  read-write
    STATUS      current
    DESCRIPTION
	"The power of phase one"
    ::= { slave6PhaseTwo 12}
	
slave6PhaseTwoVoltageMax OBJECT-TYPE
    SYNTAX      DisplayString
    MAX-ACCESS  read-write
    STATUS      current
    DESCRIPTION
	"The power of phase one"
    ::= { slave6PhaseTwo 13}
	
	
slave6PhaseThree OBJECT IDENTIFIER ::= { slave6Phase 3}	    
slave6PhaseThreeCurrent OBJECT-TYPE
    SYNTAX      DisplayString
    MAX-ACCESS  read-only
    STATUS      current
    DESCRIPTION
	"The power of phase one"
    ::= { slave6PhaseThree 1}

slave6PhaseThreeVoltage OBJECT-TYPE
    SYNTAX      DisplayString
    MAX-ACCESS  read-only
    STATUS      current
    DESCRIPTION
	"The power of phase one"
    ::= { slave6PhaseThree 2}

slave6PhaseThreePower OBJECT-TYPE
    SYNTAX      DisplayString
    MAX-ACCESS  read-only
    STATUS      current
    DESCRIPTION
	"The power of phase one"
    ::= { slave6PhaseThree 3}
	
slave6PhaseThreePowerfactor OBJECT-TYPE
    SYNTAX      DisplayString
    MAX-ACCESS  read-only
    STATUS      current
    DESCRIPTION
	"The power of phase one"
    ::= { slave6PhaseThree 4}	
	
slave6PhaseThreeEnergy OBJECT-TYPE
    SYNTAX      DisplayString
    MAX-ACCESS  read-only
    STATUS      current
    DESCRIPTION
	"The power of phase one"
    ::= { slave6PhaseThree 5}	
		
slave6PhaseThreeCurrentMin OBJECT-TYPE
    SYNTAX      DisplayString
    MAX-ACCESS  read-write
    STATUS      current
    DESCRIPTION
	"The power of phase one"
    ::= { slave6PhaseThree 6}	
	
slave6PhaseThreeCurrentMinCritical OBJECT-TYPE
    SYNTAX      DisplayString
    MAX-ACCESS  read-write
    STATUS      current
    DESCRIPTION
	"The power of phase one"
    ::= { slave6PhaseThree 7}
	
slave6PhaseThreeCurrentMaxCritical OBJECT-TYPE
    SYNTAX      DisplayString
    MAX-ACCESS  read-write
    STATUS      current
    DESCRIPTION
	"The power of phase one"
    ::= { slave6PhaseThree 8}
	
slave6PhaseThreeCurrentMax OBJECT-TYPE
    SYNTAX      DisplayString
    MAX-ACCESS  read-write
    STATUS      current
    DESCRIPTION
	"The power of phase one"
    ::= { slave6PhaseThree 9}
	
slave6PhaseThreeVoltageMin OBJECT-TYPE
    SYNTAX      DisplayString
    MAX-ACCESS  read-write
    STATUS      current
    DESCRIPTION
	"The power of phase one"
    ::= { slave6PhaseThree 10}
	
slave6PhaseThreeVoltageMinCritical OBJECT-TYPE
    SYNTAX      DisplayString
    MAX-ACCESS  read-write
    STATUS      current
    DESCRIPTION
	"The power of phase one"
    ::= { slave6PhaseThree 11}

slave6PhaseThreeVoltageMaxCritical OBJECT-TYPE
    SYNTAX      DisplayString
    MAX-ACCESS  read-write
    STATUS      current
    DESCRIPTION
	"The power of phase one"
    ::= { slave6PhaseThree 12}
	
slave6PhaseThreeVoltageMax OBJECT-TYPE
    SYNTAX      DisplayString
    MAX-ACCESS  read-write
    STATUS      current
    DESCRIPTION
	"The power of phase one"
    ::= { slave6PhaseThree 13}
	
	
-------------------------------slave6 circuit--------------------	
slave6Circuit OBJECT IDENTIFIER ::= { slave6 3}	

slave6CircuitOne OBJECT IDENTIFIER ::= { slave6Circuit 1}	    
slave6CircuitOneBreaker OBJECT-TYPE
    SYNTAX      DisplayString
    MAX-ACCESS  read-only
    STATUS      current
    DESCRIPTION
	"The power of phase one"
    ::= { slave6CircuitOne 1}
	
slave6CircuitOneManagementBit OBJECT-TYPE
    SYNTAX      DisplayString
    MAX-ACCESS  read-only
    STATUS      current
    DESCRIPTION
	"The power of phase one"
    ::= { slave6CircuitOne 2}	

slave6CircuitOneCurrent OBJECT-TYPE
    SYNTAX      DisplayString
    MAX-ACCESS  read-only
    STATUS      current
    DESCRIPTION
	"The power of phase one"
    ::= { slave6CircuitOne 3}

slave6CircuitOneVoltage OBJECT-TYPE
    SYNTAX      DisplayString
    MAX-ACCESS  read-only
    STATUS      current
    DESCRIPTION
	"The power of phase one"
    ::= { slave6CircuitOne 4}

slave6CircuitOneEnergy OBJECT-TYPE
    SYNTAX      DisplayString
    MAX-ACCESS  read-only
    STATUS      current
    DESCRIPTION
	"The power of phase one"
    ::= { slave6CircuitOne 5}	
	
slave6CircuitOnePower OBJECT-TYPE
    SYNTAX      DisplayString
    MAX-ACCESS  read-only
    STATUS      current
    DESCRIPTION
	"The power of phase one"
    ::= { slave6CircuitOne 6}
	
slave6CircuitOneCurrentMin OBJECT-TYPE
    SYNTAX      DisplayString
    MAX-ACCESS  read-write
    STATUS      current
    DESCRIPTION
	"The power of phase one"
    ::= { slave6CircuitOne 7}	
	
slave6CircuitOneCurrentMinCritical OBJECT-TYPE
    SYNTAX      DisplayString
    MAX-ACCESS  read-write
    STATUS      current
    DESCRIPTION
	"The power of phase one"
    ::= { slave6CircuitOne 8}
	
slave6CircuitOneCurrentMaxCritical OBJECT-TYPE
    SYNTAX      DisplayString
    MAX-ACCESS  read-write
    STATUS      current
    DESCRIPTION
	"The power of phase one"
    ::= { slave6CircuitOne 9}
	
slave6CircuitOneCurrentMax OBJECT-TYPE
    SYNTAX      DisplayString
    MAX-ACCESS  read-write
    STATUS      current
    DESCRIPTION
	"The power of phase one"
    ::= { slave6CircuitOne 10}
	

slave6CircuitTwo OBJECT IDENTIFIER ::= { slave6Circuit 2}	    
slave6CircuitTwoBreaker OBJECT-TYPE
    SYNTAX      DisplayString
    MAX-ACCESS  read-only
    STATUS      current
    DESCRIPTION
	"The power of phase one"
    ::= { slave6CircuitTwo 1}
	
slave6CircuitTwoManagementBit OBJECT-TYPE
    SYNTAX      DisplayString
    MAX-ACCESS  read-only
    STATUS      current
    DESCRIPTION
	"The power of phase one"
    ::= { slave6CircuitTwo 2}	

slave6CircuitTwoCurrent OBJECT-TYPE
    SYNTAX      DisplayString
    MAX-ACCESS  read-only
    STATUS      current
    DESCRIPTION
	"The power of phase one"
    ::= { slave6CircuitTwo 3}

slave6CircuitTwoVoltage OBJECT-TYPE
    SYNTAX      DisplayString
    MAX-ACCESS  read-only
    STATUS      current
    DESCRIPTION
	"The power of phase one"
    ::= { slave6CircuitTwo 4}

slave6CircuitTwoEnergy OBJECT-TYPE
    SYNTAX      DisplayString
    MAX-ACCESS  read-only
    STATUS      current
    DESCRIPTION
	"The power of phase one"
    ::= { slave6CircuitTwo 5}	
	
slave6CircuitTwoPower OBJECT-TYPE
    SYNTAX      DisplayString
    MAX-ACCESS  read-only
    STATUS      current
    DESCRIPTION
	"The power of phase one"
    ::= { slave6CircuitTwo 6}
	
slave6CircuitTwoCurrentMin OBJECT-TYPE
    SYNTAX      DisplayString
    MAX-ACCESS  read-write
    STATUS      current
    DESCRIPTION
	"The power of phase one"
    ::= { slave6CircuitTwo 7}	
	
slave6CircuitTwoCurrentMinCritical OBJECT-TYPE
    SYNTAX      DisplayString
    MAX-ACCESS  read-write
    STATUS      current
    DESCRIPTION
	"The power of phase one"
    ::= { slave6CircuitTwo 8}
	
slave6CircuitTwoCurrentMaxCritical OBJECT-TYPE
    SYNTAX      DisplayString
    MAX-ACCESS  read-write
    STATUS      current
    DESCRIPTION
	"The power of phase one"
    ::= { slave6CircuitTwo 9}
	
slave6CircuitTwoCurrentMax OBJECT-TYPE
    SYNTAX      DisplayString
    MAX-ACCESS  read-write
    STATUS      current
    DESCRIPTION
	"The power of phase one"
    ::= { slave6CircuitTwo 10}
	
	
slave6CircuitThree OBJECT IDENTIFIER ::= { slave6Circuit 3}	    
slave6CircuitThreeBreaker OBJECT-TYPE
    SYNTAX      DisplayString
    MAX-ACCESS  read-only
    STATUS      current
    DESCRIPTION
	"The power of phase one"
    ::= { slave6CircuitThree 1}
	
slave6CircuitThreeManagementBit OBJECT-TYPE
    SYNTAX      DisplayString
    MAX-ACCESS  read-only
    STATUS      current
    DESCRIPTION
	"The power of phase one"
    ::= { slave6CircuitThree 2}	

slave6CircuitThreeCurrent OBJECT-TYPE
    SYNTAX      DisplayString
    MAX-ACCESS  read-only
    STATUS      current
    DESCRIPTION
	"The power of phase one"
    ::= { slave6CircuitThree 3}

slave6CircuitThreeVoltage OBJECT-TYPE
    SYNTAX      DisplayString
    MAX-ACCESS  read-only
    STATUS      current
    DESCRIPTION
	"The power of phase one"
    ::= { slave6CircuitThree 4}

slave6CircuitThreeEnergy OBJECT-TYPE
    SYNTAX      DisplayString
    MAX-ACCESS  read-only
    STATUS      current
    DESCRIPTION
	"The power of phase one"
    ::= { slave6CircuitThree 5}	
	
slave6CircuitThreePower OBJECT-TYPE
    SYNTAX      DisplayString
    MAX-ACCESS  read-only
    STATUS      current
    DESCRIPTION
	"The power of phase one"
    ::= { slave6CircuitThree 6}
	
slave6CircuitThreeCurrentMin OBJECT-TYPE
    SYNTAX      DisplayString
    MAX-ACCESS  read-write
    STATUS      current
    DESCRIPTION
	"The power of phase one"
    ::= { slave6CircuitThree 7}	
	
slave6CircuitThreeCurrentMinCritical OBJECT-TYPE
    SYNTAX      DisplayString
    MAX-ACCESS  read-write
    STATUS      current
    DESCRIPTION
	"The power of phase one"
    ::= { slave6CircuitThree 8}
	
slave6CircuitThreeCurrentMaxCritical OBJECT-TYPE
    SYNTAX      DisplayString
    MAX-ACCESS  read-write
    STATUS      current
    DESCRIPTION
	"The power of phase one"
    ::= { slave6CircuitThree 9}
	
slave6CircuitThreeCurrentMax OBJECT-TYPE
    SYNTAX      DisplayString
    MAX-ACCESS  read-write
    STATUS      current
    DESCRIPTION
	"The power of phase one"
    ::= { slave6CircuitThree 10}
	
	
slave6CircuitFour OBJECT IDENTIFIER ::= { slave6Circuit 4}	    
slave6CircuitFourBreaker OBJECT-TYPE
    SYNTAX      DisplayString
    MAX-ACCESS  read-only
    STATUS      current
    DESCRIPTION
	"The power of phase one"
    ::= { slave6CircuitFour 1}
	
slave6CircuitFourManagementBit OBJECT-TYPE
    SYNTAX      DisplayString
    MAX-ACCESS  read-only
    STATUS      current
    DESCRIPTION
	"The power of phase one"
    ::= { slave6CircuitFour 2}	

slave6CircuitFourCurrent OBJECT-TYPE
    SYNTAX      DisplayString
    MAX-ACCESS  read-only
    STATUS      current
    DESCRIPTION
	"The power of phase one"
    ::= { slave6CircuitFour 3}

slave6CircuitFourVoltage OBJECT-TYPE
    SYNTAX      DisplayString
    MAX-ACCESS  read-only
    STATUS      current
    DESCRIPTION
	"The power of phase one"
    ::= { slave6CircuitFour 4}

slave6CircuitFourEnergy OBJECT-TYPE
    SYNTAX      DisplayString
    MAX-ACCESS  read-only
    STATUS      current
    DESCRIPTION
	"The power of phase one"
    ::= { slave6CircuitFour 5}	
	
slave6CircuitFourPower OBJECT-TYPE
    SYNTAX      DisplayString
    MAX-ACCESS  read-only
    STATUS      current
    DESCRIPTION
	"The power of phase one"
    ::= { slave6CircuitFour 6}
	
slave6CircuitFourCurrentMin OBJECT-TYPE
    SYNTAX      DisplayString
    MAX-ACCESS  read-write
    STATUS      current
    DESCRIPTION
	"The power of phase one"
    ::= { slave6CircuitFour 7}	
	
slave6CircuitFourCurrentMinCritical OBJECT-TYPE
    SYNTAX      DisplayString
    MAX-ACCESS  read-write
    STATUS      current
    DESCRIPTION
	"The power of phase one"
    ::= { slave6CircuitFour 8}
	
slave6CircuitFourCurrentMaxCritical OBJECT-TYPE
    SYNTAX      DisplayString
    MAX-ACCESS  read-write
    STATUS      current
    DESCRIPTION
	"The power of phase one"
    ::= { slave6CircuitFour 9}
	
slave6CircuitFourCurrentMax OBJECT-TYPE
    SYNTAX      DisplayString
    MAX-ACCESS  read-write
    STATUS      current
    DESCRIPTION
	"The power of phase one"
    ::= { slave6CircuitFour 10}
	
	
slave6CircuitFive OBJECT IDENTIFIER ::= { slave6Circuit 5}	    
slave6CircuitFiveBreaker OBJECT-TYPE
    SYNTAX      DisplayString
    MAX-ACCESS  read-only
    STATUS      current
    DESCRIPTION
	"The power of phase one"
    ::= { slave6CircuitFive 1}
	
slave6CircuitFiveManagementBit OBJECT-TYPE
    SYNTAX      DisplayString
    MAX-ACCESS  read-only
    STATUS      current
    DESCRIPTION
	"The power of phase one"
    ::= { slave6CircuitFive 2}	

slave6CircuitFiveCurrent OBJECT-TYPE
    SYNTAX      DisplayString
    MAX-ACCESS  read-only
    STATUS      current
    DESCRIPTION
	"The power of phase one"
    ::= { slave6CircuitFive 3}

slave6CircuitFiveVoltage OBJECT-TYPE
    SYNTAX      DisplayString
    MAX-ACCESS  read-only
    STATUS      current
    DESCRIPTION
	"The power of phase one"
    ::= { slave6CircuitFive 4}

slave6CircuitFiveEnergy OBJECT-TYPE
    SYNTAX      DisplayString
    MAX-ACCESS  read-only
    STATUS      current
    DESCRIPTION
	"The power of phase one"
    ::= { slave6CircuitFive 5}	
	
slave6CircuitFivePower OBJECT-TYPE
    SYNTAX      DisplayString
    MAX-ACCESS  read-only
    STATUS      current
    DESCRIPTION
	"The power of phase one"
    ::= { slave6CircuitFive 6}
		
slave6CircuitFiveCurrentMin OBJECT-TYPE
    SYNTAX      DisplayString
    MAX-ACCESS  read-write
    STATUS      current
    DESCRIPTION
	"The power of phase one"
    ::= { slave6CircuitFive 7}	
	
slave6CircuitFiveCurrentMinCritical OBJECT-TYPE
    SYNTAX      DisplayString
    MAX-ACCESS  read-write
    STATUS      current
    DESCRIPTION
	"The power of phase one"
    ::= { slave6CircuitFive 8}
	
slave6CircuitFiveCurrentMaxCritical OBJECT-TYPE
    SYNTAX      DisplayString
    MAX-ACCESS  read-write
    STATUS      current
    DESCRIPTION
	"The power of phase one"
    ::= { slave6CircuitFive 9}
	
slave6CircuitFiveCurrentMax OBJECT-TYPE
    SYNTAX      DisplayString
    MAX-ACCESS  read-write
    STATUS      current
    DESCRIPTION
	"The power of phase one"
    ::= { slave6CircuitFive 10}

	
slave6CircuitSix OBJECT IDENTIFIER ::= { slave6Circuit 6}	    
slave6CircuitSixBreaker OBJECT-TYPE
    SYNTAX      DisplayString
    MAX-ACCESS  read-only
    STATUS      current
    DESCRIPTION
	"The power of phase one"
    ::= { slave6CircuitSix 1}
	
slave6CircuitSixManagementBit OBJECT-TYPE
    SYNTAX      DisplayString
    MAX-ACCESS  read-only
    STATUS      current
    DESCRIPTION
	"The power of phase one"
    ::= { slave6CircuitSix 2}	

slave6CircuitSixCurrent OBJECT-TYPE
    SYNTAX      DisplayString
    MAX-ACCESS  read-only
    STATUS      current
    DESCRIPTION
	"The power of phase one"
    ::= { slave6CircuitSix 3}

slave6CircuitSixVoltage OBJECT-TYPE
    SYNTAX      DisplayString
    MAX-ACCESS  read-only
    STATUS      current
    DESCRIPTION
	"The power of phase one"
    ::= { slave6CircuitSix 4}

slave6CircuitSixEnergy OBJECT-TYPE
    SYNTAX      DisplayString
    MAX-ACCESS  read-only
    STATUS      current
    DESCRIPTION
	"The power of phase one"
    ::= { slave6CircuitSix 5}	
	
slave6CircuitSixPower OBJECT-TYPE
    SYNTAX      DisplayString
    MAX-ACCESS  read-only
    STATUS      current
    DESCRIPTION
	"The power of phase one"
    ::= { slave6CircuitSix 6}
	
slave6CircuitSixCurrentMin OBJECT-TYPE
    SYNTAX      DisplayString
    MAX-ACCESS  read-write
    STATUS      current
    DESCRIPTION
	"The power of phase one"
    ::= { slave6CircuitSix 7}	
	
slave6CircuitSixCurrentMinCritical OBJECT-TYPE
    SYNTAX      DisplayString
    MAX-ACCESS  read-write
    STATUS      current
    DESCRIPTION
	"The power of phase one"
    ::= { slave6CircuitSix 8}
	
slave6CircuitSixCurrentMaxCritical OBJECT-TYPE
    SYNTAX      DisplayString
    MAX-ACCESS  read-write
    STATUS      current
    DESCRIPTION
	"The power of phase one"
    ::= { slave6CircuitSix 9}
	
slave6CircuitSixCurrentMax OBJECT-TYPE
    SYNTAX      DisplayString
    MAX-ACCESS  read-write
    STATUS      current
    DESCRIPTION
	"The power of phase one"
    ::= { slave6CircuitSix 10}

	
-------------------------------slave6 sensor------------------------	
slave6Sensor OBJECT IDENTIFIER ::= { slave6 4}
slave6SensorTemperatureOne OBJECT-TYPE
    SYNTAX      DisplayString
    MAX-ACCESS  read-only
    STATUS      current
    DESCRIPTION
	"This is the first device."
    ::= { slave6Sensor 1}
	
slave6SensorTemperatureTwo OBJECT-TYPE
    SYNTAX      DisplayString
    MAX-ACCESS  read-only
    STATUS      current
    DESCRIPTION
	"This is the first device."
    ::= { slave6Sensor 2}

slave6SensorHumidityOne OBJECT-TYPE
    SYNTAX      DisplayString
    MAX-ACCESS  read-only
    STATUS      current
    DESCRIPTION
	"This is the first device."
    ::= { slave6Sensor 3}

slave6SensorHumidityTwo OBJECT-TYPE
    SYNTAX      DisplayString
    MAX-ACCESS  read-only
    STATUS      current
    DESCRIPTION
	"This is the first device."
    ::= { slave6Sensor 4}	

slave6SensorDoorOne OBJECT-TYPE
    SYNTAX      DisplayString
    MAX-ACCESS  read-only
    STATUS      current
    DESCRIPTION
	"This is the first device."
    ::= { slave6Sensor 5}

slave6SensorDoorTwo OBJECT-TYPE
    SYNTAX      DisplayString
    MAX-ACCESS  read-only
    STATUS      current
    DESCRIPTION
	"This is the first device."
    ::= { slave6Sensor 6}	
	
slave6SensorSmoke OBJECT-TYPE
    SYNTAX      DisplayString
    MAX-ACCESS  read-only
    STATUS      current
    DESCRIPTION
	"This is the first device."
    ::= { slave6Sensor 7}
	
slave6SensorWater OBJECT-TYPE
    SYNTAX      DisplayString
    MAX-ACCESS  read-only
    STATUS      current
    DESCRIPTION
	"This is the first device."
    ::= { slave6Sensor 8}
	
slave6SensorTemperatureOneMin OBJECT-TYPE
    SYNTAX      DisplayString
    MAX-ACCESS  read-write
    STATUS      current
    DESCRIPTION
	"This is the first device."
    ::= { slave6Sensor 9}
	
slave6SensorTemperatureOneMinCritical OBJECT-TYPE
    SYNTAX      DisplayString
    MAX-ACCESS  read-write
    STATUS      current
    DESCRIPTION
	"This is the first device."
    ::= { slave6Sensor 10}	
	
slave6SensorTemperatureOneMaxCritical OBJECT-TYPE
    SYNTAX      DisplayString
    MAX-ACCESS  read-write
    STATUS      current
    DESCRIPTION
	"This is the first device."
    ::= { slave6Sensor 11}
	
slave6SensorTemperatureOneMax OBJECT-TYPE
    SYNTAX      DisplayString
    MAX-ACCESS  read-write
    STATUS      current
    DESCRIPTION
	"This is the first device."
    ::= { slave6Sensor 12}

slave6SensorTemperatureTwoMin OBJECT-TYPE
    SYNTAX      DisplayString
    MAX-ACCESS  read-write
    STATUS      current
    DESCRIPTION
	"This is the first device."
    ::= { slave6Sensor 13}
	
slave6SensorTemperatureTwoMinCritical OBJECT-TYPE
    SYNTAX      DisplayString
    MAX-ACCESS  read-write
    STATUS      current
    DESCRIPTION
	"This is the first device."
    ::= { slave6Sensor 14}	
	
slave6SensorTemperatureTwoMaxCritical OBJECT-TYPE
    SYNTAX      DisplayString
    MAX-ACCESS  read-write
    STATUS      current
    DESCRIPTION
	"This is the first device."
    ::= { slave6Sensor 15}
	
slave6SensorTemperatureTwoMax OBJECT-TYPE
    SYNTAX      DisplayString
    MAX-ACCESS  read-write
    STATUS      current
    DESCRIPTION
	"This is the first device."
    ::= { slave6Sensor 16}
	
slave6SensorHumidityOneMin OBJECT-TYPE
    SYNTAX      DisplayString
    MAX-ACCESS  read-write
    STATUS      current
    DESCRIPTION
	"This is the first device."
    ::= { slave6Sensor 17}
	
slave6SensorHumidityOneMinCritical OBJECT-TYPE
    SYNTAX      DisplayString
    MAX-ACCESS  read-write
    STATUS      current
    DESCRIPTION
	"This is the first device."
    ::= { slave6Sensor 18}	
	
slave6SensorHumidityOneMaxCritical OBJECT-TYPE
    SYNTAX      DisplayString
    MAX-ACCESS  read-write
    STATUS      current
    DESCRIPTION
	"This is the first device."
    ::= { slave6Sensor 19}
	
slave6SensorHumidityOneMax OBJECT-TYPE
    SYNTAX      DisplayString
    MAX-ACCESS  read-write
    STATUS      current
    DESCRIPTION
	"This is the first device."
    ::= { slave6Sensor 20}

slave6SensorHumidityTwoMin OBJECT-TYPE
    SYNTAX      DisplayString
    MAX-ACCESS  read-write
    STATUS      current
    DESCRIPTION
	"This is the first device."
    ::= { slave6Sensor 21}
	
slave6SensorHumidityTwoMinCritical OBJECT-TYPE
    SYNTAX      DisplayString
    MAX-ACCESS  read-write
    STATUS      current
    DESCRIPTION
	"This is the first device."
    ::= { slave6Sensor 22}	
	
slave6SensorHumidityTwoMaxCritical OBJECT-TYPE
    SYNTAX      DisplayString
    MAX-ACCESS  read-write
    STATUS      current
    DESCRIPTION
	"This is the first device."
    ::= { slave6Sensor 23}
	
slave6SensorHumidityTwoMax OBJECT-TYPE
    SYNTAX      DisplayString
    MAX-ACCESS  read-write
    STATUS      current
    DESCRIPTION
	"This is the first device."
    ::= { slave6Sensor 24}
	
-------------------------------slave6 output name------------------------	
slave6OutputName OBJECT IDENTIFIER ::= { slave6 5}
slave6OutputNameOne OBJECT-TYPE
    SYNTAX      DisplayString
    MAX-ACCESS  read-write
    STATUS      current
    DESCRIPTION
	"The first output name of slave6"
    ::= { slave6OutputName 1}

slave6OutputNameTwo OBJECT-TYPE
    SYNTAX      DisplayString
    MAX-ACCESS  read-write
    STATUS      current
    DESCRIPTION
	"The second output name of slave6"
    ::= { slave6OutputName 2}

slave6OutputNameThree OBJECT-TYPE
    SYNTAX      DisplayString
    MAX-ACCESS  read-write
    STATUS      current
    DESCRIPTION
	"The second output name of slave6"
    ::= { slave6OutputName 3}

slave6OutputNameFour OBJECT-TYPE
    SYNTAX      DisplayString
    MAX-ACCESS  read-write
    STATUS      current
    DESCRIPTION
	"The second output name of slave6"
    ::= { slave6OutputName 4}

slave6OutputNameFive OBJECT-TYPE
    SYNTAX      DisplayString
    MAX-ACCESS  read-write
    STATUS      current
    DESCRIPTION
	"The second output name of slave6"
    ::= { slave6OutputName 5}

slave6OutputNameSix OBJECT-TYPE
    SYNTAX      DisplayString
    MAX-ACCESS  read-write
    STATUS      current
    DESCRIPTION
	"The second output name of slave6"
    ::= { slave6OutputName 6}

slave6OutputNameSeven OBJECT-TYPE
    SYNTAX      DisplayString
    MAX-ACCESS  read-write
    STATUS      current
    DESCRIPTION
	"The second output name of slave6"
    ::= { slave6OutputName 7}

slave6OutputNameEight OBJECT-TYPE
    SYNTAX      DisplayString
    MAX-ACCESS  read-write
    STATUS      current
    DESCRIPTION
	"The second output name of slave6"
    ::= { slave6OutputName 8}

slave6OutputNameNine OBJECT-TYPE
    SYNTAX      DisplayString
    MAX-ACCESS  read-write
    STATUS      current
    DESCRIPTION
	"The second output name of slave6"
    ::= { slave6OutputName 9}

slave6OutputNameTen OBJECT-TYPE
    SYNTAX      DisplayString
    MAX-ACCESS  read-write
    STATUS      current
    DESCRIPTION
	"The second output name of slave6"
    ::= { slave6OutputName 10}

slave6OutputNameEleven OBJECT-TYPE
    SYNTAX      DisplayString
    MAX-ACCESS  read-write
    STATUS      current
    DESCRIPTION
	"The second output name of slave6"
    ::= { slave6OutputName 11}

slave6OutputNameTwel OBJECT-TYPE
    SYNTAX      DisplayString
    MAX-ACCESS  read-write
    STATUS      current
    DESCRIPTION
	"The second output name of slave6"
    ::= { slave6OutputName 12}

slave6OutputNameThirteen OBJECT-TYPE
    SYNTAX      DisplayString
    MAX-ACCESS  read-write
    STATUS      current
    DESCRIPTION
	"The second output name of slave6"
    ::= { slave6OutputName 13}

slave6OutputNameFourteen OBJECT-TYPE
    SYNTAX      DisplayString
    MAX-ACCESS  read-write
    STATUS      current
    DESCRIPTION
	"The second output name of slave6"
    ::= { slave6OutputName 14}

slave6OutputNameFifteen OBJECT-TYPE
    SYNTAX      DisplayString
    MAX-ACCESS  read-write
    STATUS      current
    DESCRIPTION
	"The second output name of slave6"
    ::= { slave6OutputName 15}

slave6OutputNameSixteen OBJECT-TYPE
    SYNTAX      DisplayString
    MAX-ACCESS  read-write
    STATUS      current
    DESCRIPTION
	"The second output name of slave6"
    ::= { slave6OutputName 16}

slave6OutputNameSeventeen OBJECT-TYPE
    SYNTAX      DisplayString
    MAX-ACCESS  read-write
    STATUS      current
    DESCRIPTION
	"The second output name of slave6"
    ::= { slave6OutputName 17}

slave6OutputNameEighteen OBJECT-TYPE
    SYNTAX      DisplayString
    MAX-ACCESS  read-write
    STATUS      current
    DESCRIPTION
	"The second output name of slave6"
    ::= { slave6OutputName 18}
	
slave6OutputNameNineteen OBJECT-TYPE
    SYNTAX      DisplayString
    MAX-ACCESS  read-write
    STATUS      current
    DESCRIPTION
	"The second output name of slave6"
    ::= { slave6OutputName 19}
	
slave6OutputNametwenty OBJECT-TYPE
    SYNTAX      DisplayString
    MAX-ACCESS  read-write
    STATUS      current
    DESCRIPTION
	"The second output name of slave6"
    ::= { slave6OutputName 20}
	
slave6OutputNameTwentyone OBJECT-TYPE
    SYNTAX      DisplayString
    MAX-ACCESS  read-write
    STATUS      current
    DESCRIPTION
	"The second output name of slave6"
    ::= { slave6OutputName 21}
	
slave6OutputNameTwentyonetwo OBJECT-TYPE
    SYNTAX      DisplayString
    MAX-ACCESS  read-write
    STATUS      current
    DESCRIPTION
	"The second output name of slave6"
    ::= { slave6OutputName 22}
	
slave6OutputNameTwentythree OBJECT-TYPE
    SYNTAX      DisplayString
    MAX-ACCESS  read-write
    STATUS      current
    DESCRIPTION
	"The second output name of slave6"
    ::= { slave6OutputName 23}
	
slave6OutputNameTwentyfour OBJECT-TYPE
    SYNTAX      DisplayString
    MAX-ACCESS  read-write
    STATUS      current
    DESCRIPTION
	"The second output name of slave6"
    ::= { slave6OutputName 24}
	
slave6OutputNameTwentyfive OBJECT-TYPE
    SYNTAX      DisplayString
    MAX-ACCESS  read-write
    STATUS      current
    DESCRIPTION
	"The second output name of slave6"
    ::= { slave6OutputName 25}
	
slave6OutputNameTwentysix OBJECT-TYPE
    SYNTAX      DisplayString
    MAX-ACCESS  read-write
    STATUS      current
    DESCRIPTION
	"The second output name of slave6"
    ::= { slave6OutputName 26}
	
slave6OutputNameTwentyseven OBJECT-TYPE
    SYNTAX      DisplayString
    MAX-ACCESS  read-write
    STATUS      current
    DESCRIPTION
	"The second output name of slave6"
    ::= { slave6OutputName 27}
	
slave6OutputNameTwentyeight OBJECT-TYPE
    SYNTAX      DisplayString
    MAX-ACCESS  read-write
    STATUS      current
    DESCRIPTION
	"The second output name of slave6"
    ::= { slave6OutputName 28}	
slave6OutputNameTwentynine OBJECT-TYPE
    SYNTAX      DisplayString
    MAX-ACCESS  read-write
    STATUS      current
    DESCRIPTION
	"The second output name of slave6"
    ::= { slave6OutputName 29}
	
slave6OutputNameThirty OBJECT-TYPE
    SYNTAX      DisplayString
    MAX-ACCESS  read-write
    STATUS      current
    DESCRIPTION
	"The second output name of slave6"
    ::= { slave6OutputName 30}
	
slave6OutputNameThirtyone OBJECT-TYPE
    SYNTAX      DisplayString
    MAX-ACCESS  read-write
    STATUS      current
    DESCRIPTION
	"The second output name of slave6"
    ::= { slave6OutputName 31}
	
slave6OutputNameThirtytwo OBJECT-TYPE
    SYNTAX      DisplayString
    MAX-ACCESS  read-write
    STATUS      current
    DESCRIPTION
	"The second output name of slave6"
    ::= { slave6OutputName 32}
	
slave6OutputNameThirtythree OBJECT-TYPE
    SYNTAX      DisplayString
    MAX-ACCESS  read-write
    STATUS      current
    DESCRIPTION
	"The second output name of slave6"
    ::= { slave6OutputName 33}
	
slave6OutputNameThirtyfour OBJECT-TYPE
    SYNTAX      DisplayString
    MAX-ACCESS  read-write
    STATUS      current
    DESCRIPTION
	"The second output name of slave6"
    ::= { slave6OutputName 34}
	
slave6OutputNameThirtyfive OBJECT-TYPE
    SYNTAX      DisplayString
    MAX-ACCESS  read-write
    STATUS      current
    DESCRIPTION
	"The second output name of slave6"
    ::= { slave6OutputName 35}
	
slave6OutputNameThirtysix OBJECT-TYPE
    SYNTAX      DisplayString
    MAX-ACCESS  read-write
    STATUS      current
    DESCRIPTION
	"The second output name of slave6"
    ::= { slave6OutputName 36}
	
slave6OutputNameThirtyseven OBJECT-TYPE
    SYNTAX      DisplayString
    MAX-ACCESS  read-write
    STATUS      current
    DESCRIPTION
	"The second output name of slave6"
    ::= { slave6OutputName 37}
	
slave6OutputNameThirtyeight OBJECT-TYPE
    SYNTAX      DisplayString
    MAX-ACCESS  read-write
    STATUS      current
    DESCRIPTION
	"The second output name of slave6"
    ::= { slave6OutputName 38}
	
slave6OutputNameThirtynine OBJECT-TYPE
    SYNTAX      DisplayString
    MAX-ACCESS  read-write
    STATUS      current
    DESCRIPTION
	"The second output name of slave6"
    ::= { slave6OutputName 39}
	
slave6OutputNameFourty OBJECT-TYPE
    SYNTAX      DisplayString
    MAX-ACCESS  read-write
    STATUS      current
    DESCRIPTION
	"The second output name of slave6"
    ::= { slave6OutputName 40}
	
slave6OutputNameFourtyone OBJECT-TYPE
    SYNTAX      DisplayString
    MAX-ACCESS  read-write
    STATUS      current
    DESCRIPTION
	"The second output name of slave6"
    ::= { slave6OutputName 41}
	
slave6OutputNameFourtytwo OBJECT-TYPE
    SYNTAX      DisplayString
    MAX-ACCESS  read-write
    STATUS      current
    DESCRIPTION
	"The second output name of slave6"
    ::= { slave6OutputName 42}	

	
-------------------------------slave6 output delay------------------------	
slave6OutputDelay OBJECT IDENTIFIER ::= { slave6 6}	
slave6OutputDelayOne OBJECT-TYPE
    SYNTAX      DisplayString
    MAX-ACCESS  read-write
    STATUS      current
    DESCRIPTION
	"The first output name of slave6"
    ::= { slave6OutputDelay 1}

slave6OutputDelayTwo OBJECT-TYPE
    SYNTAX      DisplayString
    MAX-ACCESS  read-write
    STATUS      current
    DESCRIPTION
	"The second output name of slave6"
    ::= { slave6OutputDelay 2}

slave6OutputDelayThree OBJECT-TYPE
    SYNTAX      DisplayString
    MAX-ACCESS  read-write
    STATUS      current
    DESCRIPTION
	"The second output name of slave6"
    ::= { slave6OutputDelay 3}

slave6OutputDelayFour OBJECT-TYPE
    SYNTAX      DisplayString
    MAX-ACCESS  read-write
    STATUS      current
    DESCRIPTION
	"The second output name of slave6"
    ::= { slave6OutputDelay 4}

slave6OutputDelayFive OBJECT-TYPE
    SYNTAX      DisplayString
    MAX-ACCESS  read-write
    STATUS      current
    DESCRIPTION
	"The second output name of slave6"
    ::= { slave6OutputDelay 5}

slave6OutputDelaySix OBJECT-TYPE
    SYNTAX      DisplayString
    MAX-ACCESS  read-write
    STATUS      current
    DESCRIPTION
	"The second output name of slave6"
    ::= { slave6OutputDelay 6}

slave6OutputDelaySeven OBJECT-TYPE
    SYNTAX      DisplayString
    MAX-ACCESS  read-write
    STATUS      current
    DESCRIPTION
	"The second output name of slave6"
    ::= { slave6OutputDelay 7}

slave6OutputDelayEight OBJECT-TYPE
    SYNTAX      DisplayString
    MAX-ACCESS  read-write
    STATUS      current
    DESCRIPTION
	"The second output name of slave6"
    ::= { slave6OutputDelay 8}

slave6OutputDelayNine OBJECT-TYPE
    SYNTAX      DisplayString
    MAX-ACCESS  read-write
    STATUS      current
    DESCRIPTION
	"The second output name of slave6"
    ::= { slave6OutputDelay 9}

slave6OutputDelayTen OBJECT-TYPE
    SYNTAX      DisplayString
    MAX-ACCESS  read-write
    STATUS      current
    DESCRIPTION
	"The second output name of slave6"
    ::= { slave6OutputDelay 10}

slave6OutputDelayEleven OBJECT-TYPE
    SYNTAX      DisplayString
    MAX-ACCESS  read-write
    STATUS      current
    DESCRIPTION
	"The second output name of slave6"
    ::= { slave6OutputDelay 11}

slave6OutputDelayTwel OBJECT-TYPE
    SYNTAX      DisplayString
    MAX-ACCESS  read-write
    STATUS      current
    DESCRIPTION
	"The second output name of slave6"
    ::= { slave6OutputDelay 12}

slave6OutputDelayThirteen OBJECT-TYPE
    SYNTAX      DisplayString
    MAX-ACCESS  read-write
    STATUS      current
    DESCRIPTION
	"The second output name of slave6"
    ::= { slave6OutputDelay 13}

slave6OutputDelayFourteen OBJECT-TYPE
    SYNTAX      DisplayString
    MAX-ACCESS  read-write
    STATUS      current
    DESCRIPTION
	"The second output name of slave6"
    ::= { slave6OutputDelay 14}

slave6OutputDelayFifteen OBJECT-TYPE
    SYNTAX      DisplayString
    MAX-ACCESS  read-write
    STATUS      current
    DESCRIPTION
	"The second output name of slave6"
    ::= { slave6OutputDelay 15}

slave6OutputDelaySixteen OBJECT-TYPE
    SYNTAX      DisplayString
    MAX-ACCESS  read-write
    STATUS      current
    DESCRIPTION
	"The second output name of slave6"
    ::= { slave6OutputDelay 16}

slave6OutputDelaySeventeen OBJECT-TYPE
    SYNTAX      DisplayString
    MAX-ACCESS  read-write
    STATUS      current
    DESCRIPTION
	"The second output name of slave6"
    ::= { slave6OutputDelay 17}

slave6OutputDelayEighteen OBJECT-TYPE
    SYNTAX      DisplayString
    MAX-ACCESS  read-write
    STATUS      current
    DESCRIPTION
	"The second output name of slave6"
    ::= { slave6OutputDelay 18}
	
slave6OutputDelayNineteen OBJECT-TYPE
    SYNTAX      DisplayString
    MAX-ACCESS  read-write
    STATUS      current
    DESCRIPTION
	"The second output name of slave6"
    ::= { slave6OutputDelay 19}
	
slave6OutputDelaytwenty OBJECT-TYPE
    SYNTAX      DisplayString
    MAX-ACCESS  read-write
    STATUS      current
    DESCRIPTION
	"The second output name of slave6"
    ::= { slave6OutputDelay 20}
	
slave6OutputDelayTwentyone OBJECT-TYPE
    SYNTAX      DisplayString
    MAX-ACCESS  read-write
    STATUS      current
    DESCRIPTION
	"The second output name of slave6"
    ::= { slave6OutputDelay 21}
	
slave6OutputDelayTwentyonetwo OBJECT-TYPE
    SYNTAX      DisplayString
    MAX-ACCESS  read-write
    STATUS      current
    DESCRIPTION
	"The second output name of slave6"
    ::= { slave6OutputDelay 22}
	
slave6OutputDelayTwentythree OBJECT-TYPE
    SYNTAX      DisplayString
    MAX-ACCESS  read-write
    STATUS      current
    DESCRIPTION
	"The second output name of slave6"
    ::= { slave6OutputDelay 23}
	
slave6OutputDelayTwentyfour OBJECT-TYPE
    SYNTAX      DisplayString
    MAX-ACCESS  read-write
    STATUS      current
    DESCRIPTION
	"The second output name of slave6"
    ::= { slave6OutputDelay 24}
	
slave6OutputDelayTwentyfive OBJECT-TYPE
    SYNTAX      DisplayString
    MAX-ACCESS  read-write
    STATUS      current
    DESCRIPTION
	"The second output name of slave6"
    ::= { slave6OutputDelay 25}
	
slave6OutputDelayTwentysix OBJECT-TYPE
    SYNTAX      DisplayString
    MAX-ACCESS  read-write
    STATUS      current
    DESCRIPTION
	"The second output name of slave6"
    ::= { slave6OutputDelay 26}
	
slave6OutputDelayTwentyseven OBJECT-TYPE
    SYNTAX      DisplayString
    MAX-ACCESS  read-write
    STATUS      current
    DESCRIPTION
	"The second output name of slave6"
    ::= { slave6OutputDelay 27}
	
slave6OutputDelayTwentyeight OBJECT-TYPE
    SYNTAX      DisplayString
    MAX-ACCESS  read-write
    STATUS      current
    DESCRIPTION
	"The second output name of slave6"
    ::= { slave6OutputDelay 28}	
slave6OutputDelayTwentynine OBJECT-TYPE
    SYNTAX      DisplayString
    MAX-ACCESS  read-write
    STATUS      current
    DESCRIPTION
	"The second output name of slave6"
    ::= { slave6OutputDelay 29}
	
slave6OutputDelayThirty OBJECT-TYPE
    SYNTAX      DisplayString
    MAX-ACCESS  read-write
    STATUS      current
    DESCRIPTION
	"The second output name of slave6"
    ::= { slave6OutputDelay 30}
	
slave6OutputDelayThirtyone OBJECT-TYPE
    SYNTAX      DisplayString
    MAX-ACCESS  read-write
    STATUS      current
    DESCRIPTION
	"The second output name of slave6"
    ::= { slave6OutputDelay 31}
	
slave6OutputDelayThirtytwo OBJECT-TYPE
    SYNTAX      DisplayString
    MAX-ACCESS  read-write
    STATUS      current
    DESCRIPTION
	"The second output name of slave6"
    ::= { slave6OutputDelay 32}
	
slave6OutputDelayThirtythree OBJECT-TYPE
    SYNTAX      DisplayString
    MAX-ACCESS  read-write
    STATUS      current
    DESCRIPTION
	"The second output name of slave6"
    ::= { slave6OutputDelay 33}
	
slave6OutputDelayThirtyfour OBJECT-TYPE
    SYNTAX      DisplayString
    MAX-ACCESS  read-write
    STATUS      current
    DESCRIPTION
	"The second output name of slave6"
    ::= { slave6OutputDelay 34}
	
slave6OutputDelayThirtyfive OBJECT-TYPE
    SYNTAX      DisplayString
    MAX-ACCESS  read-write
    STATUS      current
    DESCRIPTION
	"The second output name of slave6"
    ::= { slave6OutputDelay 35}
	
slave6OutputDelayThirtysix OBJECT-TYPE
    SYNTAX      DisplayString
    MAX-ACCESS  read-write
    STATUS      current
    DESCRIPTION
	"The second output name of slave6"
    ::= { slave6OutputDelay 36}
	
slave6OutputDelayThirtyseven OBJECT-TYPE
    SYNTAX      DisplayString
    MAX-ACCESS  read-write
    STATUS      current
    DESCRIPTION
	"The second output name of slave6"
    ::= { slave6OutputDelay 37}
	
slave6OutputDelayThirtyeight OBJECT-TYPE
    SYNTAX      DisplayString
    MAX-ACCESS  read-write
    STATUS      current
    DESCRIPTION
	"The second output name of slave6"
    ::= { slave6OutputDelay 38}
	
slave6OutputDelayThirtynine OBJECT-TYPE
    SYNTAX      DisplayString
    MAX-ACCESS  read-write
    STATUS      current
    DESCRIPTION
	"The second output name of slave6"
    ::= { slave6OutputDelay 39}
	
slave6OutputDelayFourty OBJECT-TYPE
    SYNTAX      DisplayString
    MAX-ACCESS  read-write
    STATUS      current
    DESCRIPTION
	"The second output name of slave6"
    ::= { slave6OutputDelay 40}
	
slave6OutputDelayFourtyone OBJECT-TYPE
    SYNTAX      DisplayString
    MAX-ACCESS  read-write
    STATUS      current
    DESCRIPTION
	"The second output name of slave6"
    ::= { slave6OutputDelay 41}
	
slave6OutputDelayFourtytwo OBJECT-TYPE
    SYNTAX      DisplayString
    MAX-ACCESS  read-write
    STATUS      current
    DESCRIPTION
	"The second output name of slave6"
    ::= { slave6OutputDelay 42}

	
-------------------------------slave6 output switch------------------------	
slave6OutputSwitch OBJECT IDENTIFIER ::= { slave6 7}		
slave6OutputSwitchOne OBJECT-TYPE
    SYNTAX      DisplayString
    MAX-ACCESS  read-write
    STATUS      current
    DESCRIPTION
	"The first output name of slave6"
    ::= { slave6OutputSwitch 1}

slave6OutputSwitchTwo OBJECT-TYPE
    SYNTAX      DisplayString
    MAX-ACCESS  read-write
    STATUS      current
    DESCRIPTION
	"The second output name of slave6"
    ::= { slave6OutputSwitch 2}

slave6OutputSwitchThree OBJECT-TYPE
    SYNTAX      DisplayString
    MAX-ACCESS  read-write
    STATUS      current
    DESCRIPTION
	"The second output name of slave6"
    ::= { slave6OutputSwitch 3}

slave6OutputSwitchFour OBJECT-TYPE
    SYNTAX      DisplayString
    MAX-ACCESS  read-write
    STATUS      current
    DESCRIPTION
	"The second output name of slave6"
    ::= { slave6OutputSwitch 4}

slave6OutputSwitchFive OBJECT-TYPE
    SYNTAX      DisplayString
    MAX-ACCESS  read-write
    STATUS      current
    DESCRIPTION
	"The second output name of slave6"
    ::= { slave6OutputSwitch 5}

slave6OutputSwitchSix OBJECT-TYPE
    SYNTAX      DisplayString
    MAX-ACCESS  read-write
    STATUS      current
    DESCRIPTION
	"The second output name of slave6"
    ::= { slave6OutputSwitch 6}

slave6OutputSwitchSeven OBJECT-TYPE
    SYNTAX      DisplayString
    MAX-ACCESS  read-write
    STATUS      current
    DESCRIPTION
	"The second output name of slave6"
    ::= { slave6OutputSwitch 7}

slave6OutputSwitchEight OBJECT-TYPE
    SYNTAX      DisplayString
    MAX-ACCESS  read-write
    STATUS      current
    DESCRIPTION
	"The second output name of slave6"
    ::= { slave6OutputSwitch 8}

slave6OutputSwitchNine OBJECT-TYPE
    SYNTAX      DisplayString
    MAX-ACCESS  read-write
    STATUS      current
    DESCRIPTION
	"The second output name of slave6"
    ::= { slave6OutputSwitch 9}

slave6OutputSwitchTen OBJECT-TYPE
    SYNTAX      DisplayString
    MAX-ACCESS  read-write
    STATUS      current
    DESCRIPTION
	"The second output name of slave6"
    ::= { slave6OutputSwitch 10}

slave6OutputSwitchEleven OBJECT-TYPE
    SYNTAX      DisplayString
    MAX-ACCESS  read-write
    STATUS      current
    DESCRIPTION
	"The second output name of slave6"
    ::= { slave6OutputSwitch 11}

slave6OutputSwitchTwel OBJECT-TYPE
    SYNTAX      DisplayString
    MAX-ACCESS  read-write
    STATUS      current
    DESCRIPTION
	"The second output name of slave6"
    ::= { slave6OutputSwitch 12}

slave6OutputSwitchThirteen OBJECT-TYPE
    SYNTAX      DisplayString
    MAX-ACCESS  read-write
    STATUS      current
    DESCRIPTION
	"The second output name of slave6"
    ::= { slave6OutputSwitch 13}

slave6OutputSwitchFourteen OBJECT-TYPE
    SYNTAX      DisplayString
    MAX-ACCESS  read-write
    STATUS      current
    DESCRIPTION
	"The second output name of slave6"
    ::= { slave6OutputSwitch 14}

slave6OutputSwitchFifteen OBJECT-TYPE
    SYNTAX      DisplayString
    MAX-ACCESS  read-write
    STATUS      current
    DESCRIPTION
	"The second output name of slave6"
    ::= { slave6OutputSwitch 15}

slave6OutputSwitchSixteen OBJECT-TYPE
    SYNTAX      DisplayString
    MAX-ACCESS  read-write
    STATUS      current
    DESCRIPTION
	"The second output name of slave6"
    ::= { slave6OutputSwitch 16}

slave6OutputSwitchSeventeen OBJECT-TYPE
    SYNTAX      DisplayString
    MAX-ACCESS  read-write
    STATUS      current
    DESCRIPTION
	"The second output name of slave6"
    ::= { slave6OutputSwitch 17}

slave6OutputSwitchEighteen OBJECT-TYPE
    SYNTAX      DisplayString
    MAX-ACCESS  read-write
    STATUS      current
    DESCRIPTION
	"The second output name of slave6"
    ::= { slave6OutputSwitch 18}
	
slave6OutputSwitchNineteen OBJECT-TYPE
    SYNTAX      DisplayString
    MAX-ACCESS  read-write
    STATUS      current
    DESCRIPTION
	"The second output name of slave6"
    ::= { slave6OutputSwitch 19}
	
slave6OutputSwitchtwenty OBJECT-TYPE
    SYNTAX      DisplayString
    MAX-ACCESS  read-write
    STATUS      current
    DESCRIPTION
	"The second output name of slave6"
    ::= { slave6OutputSwitch 20}
	
slave6OutputSwitchTwentyone OBJECT-TYPE
    SYNTAX      DisplayString
    MAX-ACCESS  read-write
    STATUS      current
    DESCRIPTION
	"The second output name of slave6"
    ::= { slave6OutputSwitch 21}
	
slave6OutputSwitchTwentyonetwo OBJECT-TYPE
    SYNTAX      DisplayString
    MAX-ACCESS  read-write
    STATUS      current
    DESCRIPTION
	"The second output name of slave6"
    ::= { slave6OutputSwitch 22}
	
slave6OutputSwitchTwentythree OBJECT-TYPE
    SYNTAX      DisplayString
    MAX-ACCESS  read-write
    STATUS      current
    DESCRIPTION
	"The second output name of slave6"
    ::= { slave6OutputSwitch 23}
	
slave6OutputSwitchTwentyfour OBJECT-TYPE
    SYNTAX      DisplayString
    MAX-ACCESS  read-write
    STATUS      current
    DESCRIPTION
	"The second output name of slave6"
    ::= { slave6OutputSwitch 24}
	
slave6OutputSwitchTwentyfive OBJECT-TYPE
    SYNTAX      DisplayString
    MAX-ACCESS  read-write
    STATUS      current
    DESCRIPTION
	"The second output name of slave6"
    ::= { slave6OutputSwitch 25}
	
slave6OutputSwitchTwentysix OBJECT-TYPE
    SYNTAX      DisplayString
    MAX-ACCESS  read-write
    STATUS      current
    DESCRIPTION
	"The second output name of slave6"
    ::= { slave6OutputSwitch 26}
	
slave6OutputSwitchTwentyseven OBJECT-TYPE
    SYNTAX      DisplayString
    MAX-ACCESS  read-write
    STATUS      current
    DESCRIPTION
	"The second output name of slave6"
    ::= { slave6OutputSwitch 27}
	
slave6OutputSwitchTwentyeight OBJECT-TYPE
    SYNTAX      DisplayString
    MAX-ACCESS  read-write
    STATUS      current
    DESCRIPTION
	"The second output name of slave6"
    ::= { slave6OutputSwitch 28}	
slave6OutputSwitchTwentynine OBJECT-TYPE
    SYNTAX      DisplayString
    MAX-ACCESS  read-write
    STATUS      current
    DESCRIPTION
	"The second output name of slave6"
    ::= { slave6OutputSwitch 29}
	
slave6OutputSwitchThirty OBJECT-TYPE
    SYNTAX      DisplayString
    MAX-ACCESS  read-write
    STATUS      current
    DESCRIPTION
	"The second output name of slave6"
    ::= { slave6OutputSwitch 30}
	
slave6OutputSwitchThirtyone OBJECT-TYPE
    SYNTAX      DisplayString
    MAX-ACCESS  read-write
    STATUS      current
    DESCRIPTION
	"The second output name of slave6"
    ::= { slave6OutputSwitch 31}
	
slave6OutputSwitchThirtytwo OBJECT-TYPE
    SYNTAX      DisplayString
    MAX-ACCESS  read-write
    STATUS      current
    DESCRIPTION
	"The second output name of slave6"
    ::= { slave6OutputSwitch 32}
	
slave6OutputSwitchThirtythree OBJECT-TYPE
    SYNTAX      DisplayString
    MAX-ACCESS  read-write
    STATUS      current
    DESCRIPTION
	"The second output name of slave6"
    ::= { slave6OutputSwitch 33}
	
slave6OutputSwitchThirtyfour OBJECT-TYPE
    SYNTAX      DisplayString
    MAX-ACCESS  read-write
    STATUS      current
    DESCRIPTION
	"The second output name of slave6"
    ::= { slave6OutputSwitch 34}
	
slave6OutputSwitchThirtyfive OBJECT-TYPE
    SYNTAX      DisplayString
    MAX-ACCESS  read-write
    STATUS      current
    DESCRIPTION
	"The second output name of slave6"
    ::= { slave6OutputSwitch 35}
	
slave6OutputSwitchThirtysix OBJECT-TYPE
    SYNTAX      DisplayString
    MAX-ACCESS  read-write
    STATUS      current
    DESCRIPTION
	"The second output name of slave6"
    ::= { slave6OutputSwitch 36}
	
slave6OutputSwitchThirtyseven OBJECT-TYPE
    SYNTAX      DisplayString
    MAX-ACCESS  read-write
    STATUS      current
    DESCRIPTION
	"The second output name of slave6"
    ::= { slave6OutputSwitch 37}
	
slave6OutputSwitchThirtyeight OBJECT-TYPE
    SYNTAX      DisplayString
    MAX-ACCESS  read-write
    STATUS      current
    DESCRIPTION
	"The second output name of slave6"
    ::= { slave6OutputSwitch 38}
	
slave6OutputSwitchThirtynine OBJECT-TYPE
    SYNTAX      DisplayString
    MAX-ACCESS  read-write
    STATUS      current
    DESCRIPTION
	"The second output name of slave6"
    ::= { slave6OutputSwitch 39}
	
slave6OutputSwitchFourty OBJECT-TYPE
    SYNTAX      DisplayString
    MAX-ACCESS  read-write
    STATUS      current
    DESCRIPTION
	"The second output name of slave6"
    ::= { slave6OutputSwitch 40}
	
slave6OutputSwitchFourtyone OBJECT-TYPE
    SYNTAX      DisplayString
    MAX-ACCESS  read-write
    STATUS      current
    DESCRIPTION
	"The second output name of slave6"
    ::= { slave6OutputSwitch 41}
	
slave6OutputSwitchFourtytwo OBJECT-TYPE
    SYNTAX      DisplayString
    MAX-ACCESS  read-write
    STATUS      current
    DESCRIPTION
	"The second output name of slave6"
    ::= { slave6OutputSwitch 42}

	
-------------------------------slave6 output current------------------------	
slave6OutputCurrent OBJECT IDENTIFIER ::= { slave6 8}		
slave6OutputCurrentValue OBJECT IDENTIFIER ::= { slave6OutputCurrent 1}	

slave6OutputCurrentValueOne OBJECT-TYPE
    SYNTAX      DisplayString
    MAX-ACCESS  read-write
    STATUS      current
    DESCRIPTION
	"The first output name of slave6"
    ::= { slave6OutputCurrentValue 1}

slave6OutputCurrentValueTwo OBJECT-TYPE
    SYNTAX      DisplayString
    MAX-ACCESS  read-write
    STATUS      current
    DESCRIPTION
	"The second output name of slave6"
    ::= { slave6OutputCurrentValue 2}

slave6OutputCurrentValueThree OBJECT-TYPE
    SYNTAX      DisplayString
    MAX-ACCESS  read-write
    STATUS      current
    DESCRIPTION
	"The second output name of slave6"
    ::= { slave6OutputCurrentValue 3}

slave6OutputCurrentValueFour OBJECT-TYPE
    SYNTAX      DisplayString
    MAX-ACCESS  read-write
    STATUS      current
    DESCRIPTION
	"The second output name of slave6"
    ::= { slave6OutputCurrentValue 4}

slave6OutputCurrentValueFive OBJECT-TYPE
    SYNTAX      DisplayString
    MAX-ACCESS  read-write
    STATUS      current
    DESCRIPTION
	"The second output name of slave6"
    ::= { slave6OutputCurrentValue 5}

slave6OutputCurrentValueSix OBJECT-TYPE
    SYNTAX      DisplayString
    MAX-ACCESS  read-write
    STATUS      current
    DESCRIPTION
	"The second output name of slave6"
    ::= { slave6OutputCurrentValue 6}

slave6OutputCurrentValueSeven OBJECT-TYPE
    SYNTAX      DisplayString
    MAX-ACCESS  read-write
    STATUS      current
    DESCRIPTION
	"The second output name of slave6"
    ::= { slave6OutputCurrentValue 7}

slave6OutputCurrentValueEight OBJECT-TYPE
    SYNTAX      DisplayString
    MAX-ACCESS  read-write
    STATUS      current
    DESCRIPTION
	"The second output name of slave6"
    ::= { slave6OutputCurrentValue 8}

slave6OutputCurrentValueNine OBJECT-TYPE
    SYNTAX      DisplayString
    MAX-ACCESS  read-write
    STATUS      current
    DESCRIPTION
	"The second output name of slave6"
    ::= { slave6OutputCurrentValue 9}

slave6OutputCurrentValueTen OBJECT-TYPE
    SYNTAX      DisplayString
    MAX-ACCESS  read-write
    STATUS      current
    DESCRIPTION
	"The second output name of slave6"
    ::= { slave6OutputCurrentValue 10}

slave6OutputCurrentValueEleven OBJECT-TYPE
    SYNTAX      DisplayString
    MAX-ACCESS  read-write
    STATUS      current
    DESCRIPTION
	"The second output name of slave6"
    ::= { slave6OutputCurrentValue 11}

slave6OutputCurrentValueTwel OBJECT-TYPE
    SYNTAX      DisplayString
    MAX-ACCESS  read-write
    STATUS      current
    DESCRIPTION
	"The second output name of slave6"
    ::= { slave6OutputCurrentValue 12}

slave6OutputCurrentValueThirteen OBJECT-TYPE
    SYNTAX      DisplayString
    MAX-ACCESS  read-write
    STATUS      current
    DESCRIPTION
	"The second output name of slave6"
    ::= { slave6OutputCurrentValue 13}

slave6OutputCurrentValueFourteen OBJECT-TYPE
    SYNTAX      DisplayString
    MAX-ACCESS  read-write
    STATUS      current
    DESCRIPTION
	"The second output name of slave6"
    ::= { slave6OutputCurrentValue 14}

slave6OutputCurrentValueFifteen OBJECT-TYPE
    SYNTAX      DisplayString
    MAX-ACCESS  read-write
    STATUS      current
    DESCRIPTION
	"The second output name of slave6"
    ::= { slave6OutputCurrentValue 15}

slave6OutputCurrentValueSixteen OBJECT-TYPE
    SYNTAX      DisplayString
    MAX-ACCESS  read-write
    STATUS      current
    DESCRIPTION
	"The second output name of slave6"
    ::= { slave6OutputCurrentValue 16}

slave6OutputCurrentValueSeventeen OBJECT-TYPE
    SYNTAX      DisplayString
    MAX-ACCESS  read-write
    STATUS      current
    DESCRIPTION
	"The second output name of slave6"
    ::= { slave6OutputCurrentValue 17}

slave6OutputCurrentValueEighteen OBJECT-TYPE
    SYNTAX      DisplayString
    MAX-ACCESS  read-write
    STATUS      current
    DESCRIPTION
	"The second output name of slave6"
    ::= { slave6OutputCurrentValue 18}
	
slave6OutputCurrentValueNineteen OBJECT-TYPE
    SYNTAX      DisplayString
    MAX-ACCESS  read-write
    STATUS      current
    DESCRIPTION
	"The second output name of slave6"
    ::= { slave6OutputCurrentValue 19}
	
slave6OutputCurrentValuetwenty OBJECT-TYPE
    SYNTAX      DisplayString
    MAX-ACCESS  read-write
    STATUS      current
    DESCRIPTION
	"The second output name of slave6"
    ::= { slave6OutputCurrentValue 20}
	
slave6OutputCurrentValueTwentyone OBJECT-TYPE
    SYNTAX      DisplayString
    MAX-ACCESS  read-write
    STATUS      current
    DESCRIPTION
	"The second output name of slave6"
    ::= { slave6OutputCurrentValue 21}
	
slave6OutputCurrentValueTwentyonetwo OBJECT-TYPE
    SYNTAX      DisplayString
    MAX-ACCESS  read-write
    STATUS      current
    DESCRIPTION
	"The second output name of slave6"
    ::= { slave6OutputCurrentValue 22}
	
slave6OutputCurrentValueTwentythree OBJECT-TYPE
    SYNTAX      DisplayString
    MAX-ACCESS  read-write
    STATUS      current
    DESCRIPTION
	"The second output name of slave6"
    ::= { slave6OutputCurrentValue 23}
	
slave6OutputCurrentValueTwentyfour OBJECT-TYPE
    SYNTAX      DisplayString
    MAX-ACCESS  read-write
    STATUS      current
    DESCRIPTION
	"The second output name of slave6"
    ::= { slave6OutputCurrentValue 24}
	
slave6OutputCurrentValueTwentyfive OBJECT-TYPE
    SYNTAX      DisplayString
    MAX-ACCESS  read-write
    STATUS      current
    DESCRIPTION
	"The second output name of slave6"
    ::= { slave6OutputCurrentValue 25}
	
slave6OutputCurrentValueTwentysix OBJECT-TYPE
    SYNTAX      DisplayString
    MAX-ACCESS  read-write
    STATUS      current
    DESCRIPTION
	"The second output name of slave6"
    ::= { slave6OutputCurrentValue 26}
	
slave6OutputCurrentValueTwentyseven OBJECT-TYPE
    SYNTAX      DisplayString
    MAX-ACCESS  read-write
    STATUS      current
    DESCRIPTION
	"The second output name of slave6"
    ::= { slave6OutputCurrentValue 27}
	
slave6OutputCurrentValueTwentyeight OBJECT-TYPE
    SYNTAX      DisplayString
    MAX-ACCESS  read-write
    STATUS      current
    DESCRIPTION
	"The second output name of slave6"
    ::= { slave6OutputCurrentValue 28}	
slave6OutputCurrentValueTwentynine OBJECT-TYPE
    SYNTAX      DisplayString
    MAX-ACCESS  read-write
    STATUS      current
    DESCRIPTION
	"The second output name of slave6"
    ::= { slave6OutputCurrentValue 29}
	
slave6OutputCurrentValueThirty OBJECT-TYPE
    SYNTAX      DisplayString
    MAX-ACCESS  read-write
    STATUS      current
    DESCRIPTION
	"The second output name of slave6"
    ::= { slave6OutputCurrentValue 30}
	
slave6OutputCurrentValueThirtyone OBJECT-TYPE
    SYNTAX      DisplayString
    MAX-ACCESS  read-write
    STATUS      current
    DESCRIPTION
	"The second output name of slave6"
    ::= { slave6OutputCurrentValue 31}
	
slave6OutputCurrentValueThirtytwo OBJECT-TYPE
    SYNTAX      DisplayString
    MAX-ACCESS  read-write
    STATUS      current
    DESCRIPTION
	"The second output name of slave6"
    ::= { slave6OutputCurrentValue 32}
	
slave6OutputCurrentValueThirtythree OBJECT-TYPE
    SYNTAX      DisplayString
    MAX-ACCESS  read-write
    STATUS      current
    DESCRIPTION
	"The second output name of slave6"
    ::= { slave6OutputCurrentValue 33}
	
slave6OutputCurrentValueThirtyfour OBJECT-TYPE
    SYNTAX      DisplayString
    MAX-ACCESS  read-write
    STATUS      current
    DESCRIPTION
	"The second output name of slave6"
    ::= { slave6OutputCurrentValue 34}
	
slave6OutputCurrentValueThirtyfive OBJECT-TYPE
    SYNTAX      DisplayString
    MAX-ACCESS  read-write
    STATUS      current
    DESCRIPTION
	"The second output name of slave6"
    ::= { slave6OutputCurrentValue 35}
	
slave6OutputCurrentValueThirtysix OBJECT-TYPE
    SYNTAX      DisplayString
    MAX-ACCESS  read-write
    STATUS      current
    DESCRIPTION
	"The second output name of slave6"
    ::= { slave6OutputCurrentValue 36}
	
slave6OutputCurrentValueThirtyseven OBJECT-TYPE
    SYNTAX      DisplayString
    MAX-ACCESS  read-write
    STATUS      current
    DESCRIPTION
	"The second output name of slave6"
    ::= { slave6OutputCurrentValue 37}
	
slave6OutputCurrentValueThirtyeight OBJECT-TYPE
    SYNTAX      DisplayString
    MAX-ACCESS  read-write
    STATUS      current
    DESCRIPTION
	"The second output name of slave6"
    ::= { slave6OutputCurrentValue 38}
	
slave6OutputCurrentValueThirtynine OBJECT-TYPE
    SYNTAX      DisplayString
    MAX-ACCESS  read-write
    STATUS      current
    DESCRIPTION
	"The second output name of slave6"
    ::= { slave6OutputCurrentValue 39}
	
slave6OutputCurrentValueFourty OBJECT-TYPE
    SYNTAX      DisplayString
    MAX-ACCESS  read-write
    STATUS      current
    DESCRIPTION
	"The second output name of slave6"
    ::= { slave6OutputCurrentValue 40}
	
slave6OutputCurrentValueFourtyone OBJECT-TYPE
    SYNTAX      DisplayString
    MAX-ACCESS  read-write
    STATUS      current
    DESCRIPTION
	"The second output name of slave6"
    ::= { slave6OutputCurrentValue 41}
	
slave6OutputCurrentValueFourtytwo OBJECT-TYPE
    SYNTAX      DisplayString
    MAX-ACCESS  read-write
    STATUS      current
    DESCRIPTION
	"The second output name of slave6"
    ::= { slave6OutputCurrentValue 42}


-------------------------------slave6 output current Min------------------------			
slave6OutputCurrentMin OBJECT IDENTIFIER ::= { slave6OutputCurrent 2}	

slave6OutputCurrentMinOne OBJECT-TYPE
    SYNTAX      DisplayString
    MAX-ACCESS  read-write
    STATUS      current
    DESCRIPTION
	"The first output Min. current alarm value of slave6"
    ::= { slave6OutputCurrentMin 1}

slave6OutputCurrentMinTwo OBJECT-TYPE
    SYNTAX      DisplayString
    MAX-ACCESS  read-write
    STATUS      current
    DESCRIPTION
	"The second output Min. current alarm value of slave6"
    ::= { slave6OutputCurrentMin 2}

slave6OutputCurrentMinThree OBJECT-TYPE
    SYNTAX      DisplayString
    MAX-ACCESS  read-write
    STATUS      current
    DESCRIPTION
	"The second output Min. current alarm value of slave6"
    ::= { slave6OutputCurrentMin 3}

slave6OutputCurrentMinFour OBJECT-TYPE
    SYNTAX      DisplayString
    MAX-ACCESS  read-write
    STATUS      current
    DESCRIPTION
	"The second output Min. current alarm value of slave6"
    ::= { slave6OutputCurrentMin 4}

slave6OutputCurrentMinFive OBJECT-TYPE
    SYNTAX      DisplayString
    MAX-ACCESS  read-write
    STATUS      current
    DESCRIPTION
	"The second output Min. current alarm value of slave6"
    ::= { slave6OutputCurrentMin 5}

slave6OutputCurrentMinSix OBJECT-TYPE
    SYNTAX      DisplayString
    MAX-ACCESS  read-write
    STATUS      current
    DESCRIPTION
	"The second output Min. current alarm value of slave6"
    ::= { slave6OutputCurrentMin 6}

slave6OutputCurrentMinSeven OBJECT-TYPE
    SYNTAX      DisplayString
    MAX-ACCESS  read-write
    STATUS      current
    DESCRIPTION
	"The second output Min. current alarm value of slave6"
    ::= { slave6OutputCurrentMin 7}

slave6OutputCurrentMinEight OBJECT-TYPE
    SYNTAX      DisplayString
    MAX-ACCESS  read-write
    STATUS      current
    DESCRIPTION
	"The second output Min. current alarm value of slave6"
    ::= { slave6OutputCurrentMin 8}

slave6OutputCurrentMinNine OBJECT-TYPE
    SYNTAX      DisplayString
    MAX-ACCESS  read-write
    STATUS      current
    DESCRIPTION
	"The second output Min. current alarm value of slave6"
    ::= { slave6OutputCurrentMin 9}

slave6OutputCurrentMinTen OBJECT-TYPE
    SYNTAX      DisplayString
    MAX-ACCESS  read-write
    STATUS      current
    DESCRIPTION
	"The second output Min. current alarm value of slave6"
    ::= { slave6OutputCurrentMin 10}

slave6OutputCurrentMinEleven OBJECT-TYPE
    SYNTAX      DisplayString
    MAX-ACCESS  read-write
    STATUS      current
    DESCRIPTION
	"The second output Min. current alarm value of slave6"
    ::= { slave6OutputCurrentMin 11}

slave6OutputCurrentMinTwel OBJECT-TYPE
    SYNTAX      DisplayString
    MAX-ACCESS  read-write
    STATUS      current
    DESCRIPTION
	"The second output Min. current alarm value of slave6"
    ::= { slave6OutputCurrentMin 12}

slave6OutputCurrentMinThirteen OBJECT-TYPE
    SYNTAX      DisplayString
    MAX-ACCESS  read-write
    STATUS      current
    DESCRIPTION
	"The second output Min. current alarm value of slave6"
    ::= { slave6OutputCurrentMin 13}

slave6OutputCurrentMinFourteen OBJECT-TYPE
    SYNTAX      DisplayString
    MAX-ACCESS  read-write
    STATUS      current
    DESCRIPTION
	"The second output Min. current alarm value of slave6"
    ::= { slave6OutputCurrentMin 14}

slave6OutputCurrentMinFifteen OBJECT-TYPE
    SYNTAX      DisplayString
    MAX-ACCESS  read-write
    STATUS      current
    DESCRIPTION
	"The second output Min. current alarm value of slave6"
    ::= { slave6OutputCurrentMin 15}

slave6OutputCurrentMinSixteen OBJECT-TYPE
    SYNTAX      DisplayString
    MAX-ACCESS  read-write
    STATUS      current
    DESCRIPTION
	"The second output Min. current alarm value of slave6"
    ::= { slave6OutputCurrentMin 16}

slave6OutputCurrentMinSeventeen OBJECT-TYPE
    SYNTAX      DisplayString
    MAX-ACCESS  read-write
    STATUS      current
    DESCRIPTION
	"The second output Min. current alarm value of slave6"
    ::= { slave6OutputCurrentMin 17}

slave6OutputCurrentMinEighteen OBJECT-TYPE
    SYNTAX      DisplayString
    MAX-ACCESS  read-write
    STATUS      current
    DESCRIPTION
	"The second output Min. current alarm value of slave6"
    ::= { slave6OutputCurrentMin 18}
	
slave6OutputCurrentMinNineteen OBJECT-TYPE
    SYNTAX      DisplayString
    MAX-ACCESS  read-write
    STATUS      current
    DESCRIPTION
	"The second output Min. current alarm value of slave6"
    ::= { slave6OutputCurrentMin 19}
	
slave6OutputCurrentMintwenty OBJECT-TYPE
    SYNTAX      DisplayString
    MAX-ACCESS  read-write
    STATUS      current
    DESCRIPTION
	"The second output Min. current alarm value of slave6"
    ::= { slave6OutputCurrentMin 20}
	
slave6OutputCurrentMinTwentyone OBJECT-TYPE
    SYNTAX      DisplayString
    MAX-ACCESS  read-write
    STATUS      current
    DESCRIPTION
	"The second output Min. current alarm value of slave6"
    ::= { slave6OutputCurrentMin 21}
	
slave6OutputCurrentMinTwentyonetwo OBJECT-TYPE
    SYNTAX      DisplayString
    MAX-ACCESS  read-write
    STATUS      current
    DESCRIPTION
	"The second output Min. current alarm value of slave6"
    ::= { slave6OutputCurrentMin 22}
	
slave6OutputCurrentMinTwentythree OBJECT-TYPE
    SYNTAX      DisplayString
    MAX-ACCESS  read-write
    STATUS      current
    DESCRIPTION
	"The second output Min. current alarm value of slave6"
    ::= { slave6OutputCurrentMin 23}
	
slave6OutputCurrentMinTwentyfour OBJECT-TYPE
    SYNTAX      DisplayString
    MAX-ACCESS  read-write
    STATUS      current
    DESCRIPTION
	"The second output Min. current alarm value of slave6"
    ::= { slave6OutputCurrentMin 24}
	
slave6OutputCurrentMinTwentyfive OBJECT-TYPE
    SYNTAX      DisplayString
    MAX-ACCESS  read-write
    STATUS      current
    DESCRIPTION
	"The second output Min. current alarm value of slave6"
    ::= { slave6OutputCurrentMin 25}
	
slave6OutputCurrentMinTwentysix OBJECT-TYPE
    SYNTAX      DisplayString
    MAX-ACCESS  read-write
    STATUS      current
    DESCRIPTION
	"The second output Min. current alarm value of slave6"
    ::= { slave6OutputCurrentMin 26}
	
slave6OutputCurrentMinTwentyseven OBJECT-TYPE
    SYNTAX      DisplayString
    MAX-ACCESS  read-write
    STATUS      current
    DESCRIPTION
	"The second output Min. current alarm value of slave6"
    ::= { slave6OutputCurrentMin 27}
	
slave6OutputCurrentMinTwentyeight OBJECT-TYPE
    SYNTAX      DisplayString
    MAX-ACCESS  read-write
    STATUS      current
    DESCRIPTION
	"The second output Min. current alarm value of slave6"
    ::= { slave6OutputCurrentMin 28}	
slave6OutputCurrentMinTwentynine OBJECT-TYPE
    SYNTAX      DisplayString
    MAX-ACCESS  read-write
    STATUS      current
    DESCRIPTION
	"The second output Min. current alarm value of slave6"
    ::= { slave6OutputCurrentMin 29}
	
slave6OutputCurrentMinThirty OBJECT-TYPE
    SYNTAX      DisplayString
    MAX-ACCESS  read-write
    STATUS      current
    DESCRIPTION
	"The second output Min. current alarm value of slave6"
    ::= { slave6OutputCurrentMin 30}
	
slave6OutputCurrentMinThirtyone OBJECT-TYPE
    SYNTAX      DisplayString
    MAX-ACCESS  read-write
    STATUS      current
    DESCRIPTION
	"The second output Min. current alarm value of slave6"
    ::= { slave6OutputCurrentMin 31}
	
slave6OutputCurrentMinThirtytwo OBJECT-TYPE
    SYNTAX      DisplayString
    MAX-ACCESS  read-write
    STATUS      current
    DESCRIPTION
	"The second output Min. current alarm value of slave6"
    ::= { slave6OutputCurrentMin 32}
	
slave6OutputCurrentMinThirtythree OBJECT-TYPE
    SYNTAX      DisplayString
    MAX-ACCESS  read-write
    STATUS      current
    DESCRIPTION
	"The second output Min. current alarm value of slave6"
    ::= { slave6OutputCurrentMin 33}
	
slave6OutputCurrentMinThirtyfour OBJECT-TYPE
    SYNTAX      DisplayString
    MAX-ACCESS  read-write
    STATUS      current
    DESCRIPTION
	"The second output Min. current alarm value of slave6"
    ::= { slave6OutputCurrentMin 34}
	
slave6OutputCurrentMinThirtyfive OBJECT-TYPE
    SYNTAX      DisplayString
    MAX-ACCESS  read-write
    STATUS      current
    DESCRIPTION
	"The second output Min. current alarm value of slave6"
    ::= { slave6OutputCurrentMin 35}
	
slave6OutputCurrentMinThirtysix OBJECT-TYPE
    SYNTAX      DisplayString
    MAX-ACCESS  read-write
    STATUS      current
    DESCRIPTION
	"The second output Min. current alarm value of slave6"
    ::= { slave6OutputCurrentMin 36}
	
slave6OutputCurrentMinThirtyseven OBJECT-TYPE
    SYNTAX      DisplayString
    MAX-ACCESS  read-write
    STATUS      current
    DESCRIPTION
	"The second output Min. current alarm value of slave6"
    ::= { slave6OutputCurrentMin 37}
	
slave6OutputCurrentMinThirtyeight OBJECT-TYPE
    SYNTAX      DisplayString
    MAX-ACCESS  read-write
    STATUS      current
    DESCRIPTION
	"The second output Min. current alarm value of slave6"
    ::= { slave6OutputCurrentMin 38}
	
slave6OutputCurrentMinThirtynine OBJECT-TYPE
    SYNTAX      DisplayString
    MAX-ACCESS  read-write
    STATUS      current
    DESCRIPTION
	"The second output Min. current alarm value of slave6"
    ::= { slave6OutputCurrentMin 39}
	
slave6OutputCurrentMinFourty OBJECT-TYPE
    SYNTAX      DisplayString
    MAX-ACCESS  read-write
    STATUS      current
    DESCRIPTION
	"The second output Min. current alarm value of slave6"
    ::= { slave6OutputCurrentMin 40}
	
slave6OutputCurrentMinFourtyone OBJECT-TYPE
    SYNTAX      DisplayString
    MAX-ACCESS  read-write
    STATUS      current
    DESCRIPTION
	"The second output Min. current alarm value of slave6"
    ::= { slave6OutputCurrentMin 41}
	
slave6OutputCurrentMinFourtytwo OBJECT-TYPE
    SYNTAX      DisplayString
    MAX-ACCESS  read-write
    STATUS      current
    DESCRIPTION
	"The second output Min. current alarm value of slave6"
    ::= { slave6OutputCurrentMin 42}


------------------------slave6 output current Min critical----------------			
slave6OutputCurrentMinCritical OBJECT IDENTIFIER ::= { slave6OutputCurrent 3}	

slave6OutputCurrentMinCriticalOne OBJECT-TYPE
    SYNTAX      DisplayString
    MAX-ACCESS  read-write
    STATUS      current
    DESCRIPTION
	"The first output Min. current warning value of slave6"
    ::= { slave6OutputCurrentMinCritical 1}

slave6OutputCurrentMinCriticalTwo OBJECT-TYPE
    SYNTAX      DisplayString
    MAX-ACCESS  read-write
    STATUS      current
    DESCRIPTION
	"The second output Min. current warning value of slave6"
    ::= { slave6OutputCurrentMinCritical 2}

slave6OutputCurrentMinCriticalThree OBJECT-TYPE
    SYNTAX      DisplayString
    MAX-ACCESS  read-write
    STATUS      current
    DESCRIPTION
	"The second output Min. current warning value of slave6"
    ::= { slave6OutputCurrentMinCritical 3}

slave6OutputCurrentMinCriticalFour OBJECT-TYPE
    SYNTAX      DisplayString
    MAX-ACCESS  read-write
    STATUS      current
    DESCRIPTION
	"The second output Min. current warning value of slave6"
    ::= { slave6OutputCurrentMinCritical 4}

slave6OutputCurrentMinCriticalFive OBJECT-TYPE
    SYNTAX      DisplayString
    MAX-ACCESS  read-write
    STATUS      current
    DESCRIPTION
	"The second output Min. current warning value of slave6"
    ::= { slave6OutputCurrentMinCritical 5}

slave6OutputCurrentMinCriticalSix OBJECT-TYPE
    SYNTAX      DisplayString
    MAX-ACCESS  read-write
    STATUS      current
    DESCRIPTION
	"The second output Min. current warning value of slave6"
    ::= { slave6OutputCurrentMinCritical 6}

slave6OutputCurrentMinCriticalSeven OBJECT-TYPE
    SYNTAX      DisplayString
    MAX-ACCESS  read-write
    STATUS      current
    DESCRIPTION
	"The second output Min. current warning value of slave6"
    ::= { slave6OutputCurrentMinCritical 7}

slave6OutputCurrentMinCriticalEight OBJECT-TYPE
    SYNTAX      DisplayString
    MAX-ACCESS  read-write
    STATUS      current
    DESCRIPTION
	"The second output Min. current warning value of slave6"
    ::= { slave6OutputCurrentMinCritical 8}

slave6OutputCurrentMinCriticalNine OBJECT-TYPE
    SYNTAX      DisplayString
    MAX-ACCESS  read-write
    STATUS      current
    DESCRIPTION
	"The second output Min. current warning value of slave6"
    ::= { slave6OutputCurrentMinCritical 9}

slave6OutputCurrentMinCriticalTen OBJECT-TYPE
    SYNTAX      DisplayString
    MAX-ACCESS  read-write
    STATUS      current
    DESCRIPTION
	"The second output Min. current warning value of slave6"
    ::= { slave6OutputCurrentMinCritical 10}

slave6OutputCurrentMinCriticalEleven OBJECT-TYPE
    SYNTAX      DisplayString
    MAX-ACCESS  read-write
    STATUS      current
    DESCRIPTION
	"The second output Min. current warning value of slave6"
    ::= { slave6OutputCurrentMinCritical 11}

slave6OutputCurrentMinCriticalTwel OBJECT-TYPE
    SYNTAX      DisplayString
    MAX-ACCESS  read-write
    STATUS      current
    DESCRIPTION
	"The second output Min. current warning value of slave6"
    ::= { slave6OutputCurrentMinCritical 12}

slave6OutputCurrentMinCriticalThirteen OBJECT-TYPE
    SYNTAX      DisplayString
    MAX-ACCESS  read-write
    STATUS      current
    DESCRIPTION
	"The second output Min. current warning value of slave6"
    ::= { slave6OutputCurrentMinCritical 13}

slave6OutputCurrentMinCriticalFourteen OBJECT-TYPE
    SYNTAX      DisplayString
    MAX-ACCESS  read-write
    STATUS      current
    DESCRIPTION
	"The second output Min. current warning value of slave6"
    ::= { slave6OutputCurrentMinCritical 14}

slave6OutputCurrentMinCriticalFifteen OBJECT-TYPE
    SYNTAX      DisplayString
    MAX-ACCESS  read-write
    STATUS      current
    DESCRIPTION
	"The second output Min. current warning value of slave6"
    ::= { slave6OutputCurrentMinCritical 15}

slave6OutputCurrentMinCriticalSixteen OBJECT-TYPE
    SYNTAX      DisplayString
    MAX-ACCESS  read-write
    STATUS      current
    DESCRIPTION
	"The second output Min. current warning value of slave6"
    ::= { slave6OutputCurrentMinCritical 16}

slave6OutputCurrentMinCriticalSeventeen OBJECT-TYPE
    SYNTAX      DisplayString
    MAX-ACCESS  read-write
    STATUS      current
    DESCRIPTION
	"The second output Min. current warning value of slave6"
    ::= { slave6OutputCurrentMinCritical 17}

slave6OutputCurrentMinCriticalEighteen OBJECT-TYPE
    SYNTAX      DisplayString
    MAX-ACCESS  read-write
    STATUS      current
    DESCRIPTION
	"The second output Min. current warning value of slave6"
    ::= { slave6OutputCurrentMinCritical 18}
	
slave6OutputCurrentMinCriticalNineteen OBJECT-TYPE
    SYNTAX      DisplayString
    MAX-ACCESS  read-write
    STATUS      current
    DESCRIPTION
	"The second output Min. current warning value of slave6"
    ::= { slave6OutputCurrentMinCritical 19}
	
slave6OutputCurrentMinCriticaltwenty OBJECT-TYPE
    SYNTAX      DisplayString
    MAX-ACCESS  read-write
    STATUS      current
    DESCRIPTION
	"The second output Min. current warning value of slave6"
    ::= { slave6OutputCurrentMinCritical 20}
	
slave6OutputCurrentMinCriticalTwentyone OBJECT-TYPE
    SYNTAX      DisplayString
    MAX-ACCESS  read-write
    STATUS      current
    DESCRIPTION
	"The second output Min. current warning value of slave6"
    ::= { slave6OutputCurrentMinCritical 21}
	
slave6OutputCurrentMinCriticalTwentyonetwo OBJECT-TYPE
    SYNTAX      DisplayString
    MAX-ACCESS  read-write
    STATUS      current
    DESCRIPTION
	"The second output Min. current warning value of slave6"
    ::= { slave6OutputCurrentMinCritical 22}
	
slave6OutputCurrentMinCriticalTwentythree OBJECT-TYPE
    SYNTAX      DisplayString
    MAX-ACCESS  read-write
    STATUS      current
    DESCRIPTION
	"The second output Min. current warning value of slave6"
    ::= { slave6OutputCurrentMinCritical 23}
	
slave6OutputCurrentMinCriticalTwentyfour OBJECT-TYPE
    SYNTAX      DisplayString
    MAX-ACCESS  read-write
    STATUS      current
    DESCRIPTION
	"The second output Min. current warning value of slave6"
    ::= { slave6OutputCurrentMinCritical 24}
	
slave6OutputCurrentMinCriticalTwentyfive OBJECT-TYPE
    SYNTAX      DisplayString
    MAX-ACCESS  read-write
    STATUS      current
    DESCRIPTION
	"The second output Min. current warning value of slave6"
    ::= { slave6OutputCurrentMinCritical 25}
	
slave6OutputCurrentMinCriticalTwentysix OBJECT-TYPE
    SYNTAX      DisplayString
    MAX-ACCESS  read-write
    STATUS      current
    DESCRIPTION
	"The second output Min. current warning value of slave6"
    ::= { slave6OutputCurrentMinCritical 26}
	
slave6OutputCurrentMinCriticalTwentyseven OBJECT-TYPE
    SYNTAX      DisplayString
    MAX-ACCESS  read-write
    STATUS      current
    DESCRIPTION
	"The second output Min. current warning value of slave6"
    ::= { slave6OutputCurrentMinCritical 27}
	
slave6OutputCurrentMinCriticalTwentyeight OBJECT-TYPE
    SYNTAX      DisplayString
    MAX-ACCESS  read-write
    STATUS      current
    DESCRIPTION
	"The second output Min. current warning value of slave6"
    ::= { slave6OutputCurrentMinCritical 28}	
slave6OutputCurrentMinCriticalTwentynine OBJECT-TYPE
    SYNTAX      DisplayString
    MAX-ACCESS  read-write
    STATUS      current
    DESCRIPTION
	"The second output Min. current warning value of slave6"
    ::= { slave6OutputCurrentMinCritical 29}
	
slave6OutputCurrentMinCriticalThirty OBJECT-TYPE
    SYNTAX      DisplayString
    MAX-ACCESS  read-write
    STATUS      current
    DESCRIPTION
	"The second output Min. current warning value of slave6"
    ::= { slave6OutputCurrentMinCritical 30}
	
slave6OutputCurrentMinCriticalThirtyone OBJECT-TYPE
    SYNTAX      DisplayString
    MAX-ACCESS  read-write
    STATUS      current
    DESCRIPTION
	"The second output Min. current warning value of slave6"
    ::= { slave6OutputCurrentMinCritical 31}
	
slave6OutputCurrentMinCriticalThirtytwo OBJECT-TYPE
    SYNTAX      DisplayString
    MAX-ACCESS  read-write
    STATUS      current
    DESCRIPTION
	"The second output Min. current warning value of slave6"
    ::= { slave6OutputCurrentMinCritical 32}
	
slave6OutputCurrentMinCriticalThirtythree OBJECT-TYPE
    SYNTAX      DisplayString
    MAX-ACCESS  read-write
    STATUS      current
    DESCRIPTION
	"The second output Min. current warning value of slave6"
    ::= { slave6OutputCurrentMinCritical 33}
	
slave6OutputCurrentMinCriticalThirtyfour OBJECT-TYPE
    SYNTAX      DisplayString
    MAX-ACCESS  read-write
    STATUS      current
    DESCRIPTION
	"The second output Min. current warning value of slave6"
    ::= { slave6OutputCurrentMinCritical 34}
	
slave6OutputCurrentMinCriticalThirtyfive OBJECT-TYPE
    SYNTAX      DisplayString
    MAX-ACCESS  read-write
    STATUS      current
    DESCRIPTION
	"The second output Min. current warning value of slave6"
    ::= { slave6OutputCurrentMinCritical 35}
	
slave6OutputCurrentMinCriticalThirtysix OBJECT-TYPE
    SYNTAX      DisplayString
    MAX-ACCESS  read-write
    STATUS      current
    DESCRIPTION
	"The second output Min. current warning value of slave6"
    ::= { slave6OutputCurrentMinCritical 36}
	
slave6OutputCurrentMinCriticalThirtyseven OBJECT-TYPE
    SYNTAX      DisplayString
    MAX-ACCESS  read-write
    STATUS      current
    DESCRIPTION
	"The second output Min. current warning value of slave6"
    ::= { slave6OutputCurrentMinCritical 37}
	
slave6OutputCurrentMinCriticalThirtyeight OBJECT-TYPE
    SYNTAX      DisplayString
    MAX-ACCESS  read-write
    STATUS      current
    DESCRIPTION
	"The second output Min. current warning value of slave6"
    ::= { slave6OutputCurrentMinCritical 38}
	
slave6OutputCurrentMinCriticalThirtynine OBJECT-TYPE
    SYNTAX      DisplayString
    MAX-ACCESS  read-write
    STATUS      current
    DESCRIPTION
	"The second output Min. current warning value of slave6"
    ::= { slave6OutputCurrentMinCritical 39}
	
slave6OutputCurrentMinCriticalFourty OBJECT-TYPE
    SYNTAX      DisplayString
    MAX-ACCESS  read-write
    STATUS      current
    DESCRIPTION
	"The second output Min. current warning value of slave6"
    ::= { slave6OutputCurrentMinCritical 40}
	
slave6OutputCurrentMinCriticalFourtyone OBJECT-TYPE
    SYNTAX      DisplayString
    MAX-ACCESS  read-write
    STATUS      current
    DESCRIPTION
	"The second output Min. current warning value of slave6"
    ::= { slave6OutputCurrentMinCritical 41}
	
slave6OutputCurrentMinCriticalFourtytwo OBJECT-TYPE
    SYNTAX      DisplayString
    MAX-ACCESS  read-write
    STATUS      current
    DESCRIPTION
	"The second output Min. current warning value of slave6"
    ::= { slave6OutputCurrentMinCritical 42}
	
	
------------------------slave6 output current Max critical----------------			
slave6OutputCurrentMaxCritical OBJECT IDENTIFIER ::= { slave6OutputCurrent 4}	

slave6OutputCurrentMaxCriticalOne OBJECT-TYPE
    SYNTAX      DisplayString
    MAX-ACCESS  read-write
    STATUS      current
    DESCRIPTION
	"The first output Max. current warning value of slave6"
    ::= { slave6OutputCurrentMaxCritical 1}

slave6OutputCurrentMaxCriticalTwo OBJECT-TYPE
    SYNTAX      DisplayString
    MAX-ACCESS  read-write
    STATUS      current
    DESCRIPTION
	"The second output Max. current warning value of slave6"
    ::= { slave6OutputCurrentMaxCritical 2}

slave6OutputCurrentMaxCriticalThree OBJECT-TYPE
    SYNTAX      DisplayString
    MAX-ACCESS  read-write
    STATUS      current
    DESCRIPTION
	"The second output Max. current warning value of slave6"
    ::= { slave6OutputCurrentMaxCritical 3}

slave6OutputCurrentMaxCriticalFour OBJECT-TYPE
    SYNTAX      DisplayString
    MAX-ACCESS  read-write
    STATUS      current
    DESCRIPTION
	"The second output Max. current warning value of slave6"
    ::= { slave6OutputCurrentMaxCritical 4}

slave6OutputCurrentMaxCriticalFive OBJECT-TYPE
    SYNTAX      DisplayString
    MAX-ACCESS  read-write
    STATUS      current
    DESCRIPTION
	"The second output Max. current warning value of slave6"
    ::= { slave6OutputCurrentMaxCritical 5}

slave6OutputCurrentMaxCriticalSix OBJECT-TYPE
    SYNTAX      DisplayString
    MAX-ACCESS  read-write
    STATUS      current
    DESCRIPTION
	"The second output Max. current warning value of slave6"
    ::= { slave6OutputCurrentMaxCritical 6}

slave6OutputCurrentMaxCriticalSeven OBJECT-TYPE
    SYNTAX      DisplayString
    MAX-ACCESS  read-write
    STATUS      current
    DESCRIPTION
	"The second output Max. current warning value of slave6"
    ::= { slave6OutputCurrentMaxCritical 7}

slave6OutputCurrentMaxCriticalEight OBJECT-TYPE
    SYNTAX      DisplayString
    MAX-ACCESS  read-write
    STATUS      current
    DESCRIPTION
	"The second output Max. current warning value of slave6"
    ::= { slave6OutputCurrentMaxCritical 8}

slave6OutputCurrentMaxCriticalNine OBJECT-TYPE
    SYNTAX      DisplayString
    MAX-ACCESS  read-write
    STATUS      current
    DESCRIPTION
	"The second output Max. current warning value of slave6"
    ::= { slave6OutputCurrentMaxCritical 9}

slave6OutputCurrentMaxCriticalTen OBJECT-TYPE
    SYNTAX      DisplayString
    MAX-ACCESS  read-write
    STATUS      current
    DESCRIPTION
	"The second output Max. current warning value of slave6"
    ::= { slave6OutputCurrentMaxCritical 10}

slave6OutputCurrentMaxCriticalEleven OBJECT-TYPE
    SYNTAX      DisplayString
    MAX-ACCESS  read-write
    STATUS      current
    DESCRIPTION
	"The second output Max. current warning value of slave6"
    ::= { slave6OutputCurrentMaxCritical 11}

slave6OutputCurrentMaxCriticalTwel OBJECT-TYPE
    SYNTAX      DisplayString
    MAX-ACCESS  read-write
    STATUS      current
    DESCRIPTION
	"The second output Max. current warning value of slave6"
    ::= { slave6OutputCurrentMaxCritical 12}

slave6OutputCurrentMaxCriticalThirteen OBJECT-TYPE
    SYNTAX      DisplayString
    MAX-ACCESS  read-write
    STATUS      current
    DESCRIPTION
	"The second output Max. current warning value of slave6"
    ::= { slave6OutputCurrentMaxCritical 13}

slave6OutputCurrentMaxCriticalFourteen OBJECT-TYPE
    SYNTAX      DisplayString
    MAX-ACCESS  read-write
    STATUS      current
    DESCRIPTION
	"The second output Max. current warning value of slave6"
    ::= { slave6OutputCurrentMaxCritical 14}

slave6OutputCurrentMaxCriticalFifteen OBJECT-TYPE
    SYNTAX      DisplayString
    MAX-ACCESS  read-write
    STATUS      current
    DESCRIPTION
	"The second output Max. current warning value of slave6"
    ::= { slave6OutputCurrentMaxCritical 15}

slave6OutputCurrentMaxCriticalSixteen OBJECT-TYPE
    SYNTAX      DisplayString
    MAX-ACCESS  read-write
    STATUS      current
    DESCRIPTION
	"The second output Max. current warning value of slave6"
    ::= { slave6OutputCurrentMaxCritical 16}

slave6OutputCurrentMaxCriticalSeventeen OBJECT-TYPE
    SYNTAX      DisplayString
    MAX-ACCESS  read-write
    STATUS      current
    DESCRIPTION
	"The second output Max. current warning value of slave6"
    ::= { slave6OutputCurrentMaxCritical 17}

slave6OutputCurrentMaxCriticalEighteen OBJECT-TYPE
    SYNTAX      DisplayString
    MAX-ACCESS  read-write
    STATUS      current
    DESCRIPTION
	"The second output Max. current warning value of slave6"
    ::= { slave6OutputCurrentMaxCritical 18}
	
slave6OutputCurrentMaxCriticalNineteen OBJECT-TYPE
    SYNTAX      DisplayString
    MAX-ACCESS  read-write
    STATUS      current
    DESCRIPTION
	"The second output Max. current warning value of slave6"
    ::= { slave6OutputCurrentMaxCritical 19}
	
slave6OutputCurrentMaxCriticaltwenty OBJECT-TYPE
    SYNTAX      DisplayString
    MAX-ACCESS  read-write
    STATUS      current
    DESCRIPTION
	"The second output Max. current warning value of slave6"
    ::= { slave6OutputCurrentMaxCritical 20}
	
slave6OutputCurrentMaxCriticalTwentyone OBJECT-TYPE
    SYNTAX      DisplayString
    MAX-ACCESS  read-write
    STATUS      current
    DESCRIPTION
	"The second output Max. current warning value of slave6"
    ::= { slave6OutputCurrentMaxCritical 21}
	
slave6OutputCurrentMaxCriticalTwentyonetwo OBJECT-TYPE
    SYNTAX      DisplayString
    MAX-ACCESS  read-write
    STATUS      current
    DESCRIPTION
	"The second output Max. current warning value of slave6"
    ::= { slave6OutputCurrentMaxCritical 22}
	
slave6OutputCurrentMaxCriticalTwentythree OBJECT-TYPE
    SYNTAX      DisplayString
    MAX-ACCESS  read-write
    STATUS      current
    DESCRIPTION
	"The second output Max. current warning value of slave6"
    ::= { slave6OutputCurrentMaxCritical 23}
	
slave6OutputCurrentMaxCriticalTwentyfour OBJECT-TYPE
    SYNTAX      DisplayString
    MAX-ACCESS  read-write
    STATUS      current
    DESCRIPTION
	"The second output Max. current warning value of slave6"
    ::= { slave6OutputCurrentMaxCritical 24}
	
slave6OutputCurrentMaxCriticalTwentyfive OBJECT-TYPE
    SYNTAX      DisplayString
    MAX-ACCESS  read-write
    STATUS      current
    DESCRIPTION
	"The second output Max. current warning value of slave6"
    ::= { slave6OutputCurrentMaxCritical 25}
	
slave6OutputCurrentMaxCriticalTwentysix OBJECT-TYPE
    SYNTAX      DisplayString
    MAX-ACCESS  read-write
    STATUS      current
    DESCRIPTION
	"The second output Max. current warning value of slave6"
    ::= { slave6OutputCurrentMaxCritical 26}
	
slave6OutputCurrentMaxCriticalTwentyseven OBJECT-TYPE
    SYNTAX      DisplayString
    MAX-ACCESS  read-write
    STATUS      current
    DESCRIPTION
	"The second output Max. current warning value of slave6"
    ::= { slave6OutputCurrentMaxCritical 27}
	
slave6OutputCurrentMaxCriticalTwentyeight OBJECT-TYPE
    SYNTAX      DisplayString
    MAX-ACCESS  read-write
    STATUS      current
    DESCRIPTION
	"The second output Max. current warning value of slave6"
    ::= { slave6OutputCurrentMaxCritical 28}	
slave6OutputCurrentMaxCriticalTwentynine OBJECT-TYPE
    SYNTAX      DisplayString
    MAX-ACCESS  read-write
    STATUS      current
    DESCRIPTION
	"The second output Max. current warning value of slave6"
    ::= { slave6OutputCurrentMaxCritical 29}
	
slave6OutputCurrentMaxCriticalThirty OBJECT-TYPE
    SYNTAX      DisplayString
    MAX-ACCESS  read-write
    STATUS      current
    DESCRIPTION
	"The second output Max. current warning value of slave6"
    ::= { slave6OutputCurrentMaxCritical 30}
	
slave6OutputCurrentMaxCriticalThirtyone OBJECT-TYPE
    SYNTAX      DisplayString
    MAX-ACCESS  read-write
    STATUS      current
    DESCRIPTION
	"The second output Max. current warning value of slave6"
    ::= { slave6OutputCurrentMaxCritical 31}
	
slave6OutputCurrentMaxCriticalThirtytwo OBJECT-TYPE
    SYNTAX      DisplayString
    MAX-ACCESS  read-write
    STATUS      current
    DESCRIPTION
	"The second output Max. current warning value of slave6"
    ::= { slave6OutputCurrentMaxCritical 32}
	
slave6OutputCurrentMaxCriticalThirtythree OBJECT-TYPE
    SYNTAX      DisplayString
    MAX-ACCESS  read-write
    STATUS      current
    DESCRIPTION
	"The second output Max. current warning value of slave6"
    ::= { slave6OutputCurrentMaxCritical 33}
	
slave6OutputCurrentMaxCriticalThirtyfour OBJECT-TYPE
    SYNTAX      DisplayString
    MAX-ACCESS  read-write
    STATUS      current
    DESCRIPTION
	"The second output Max. current warning value of slave6"
    ::= { slave6OutputCurrentMaxCritical 34}
	
slave6OutputCurrentMaxCriticalThirtyfive OBJECT-TYPE
    SYNTAX      DisplayString
    MAX-ACCESS  read-write
    STATUS      current
    DESCRIPTION
	"The second output Max. current warning value of slave6"
    ::= { slave6OutputCurrentMaxCritical 35}
	
slave6OutputCurrentMaxCriticalThirtysix OBJECT-TYPE
    SYNTAX      DisplayString
    MAX-ACCESS  read-write
    STATUS      current
    DESCRIPTION
	"The second output Max. current warning value of slave6"
    ::= { slave6OutputCurrentMaxCritical 36}
	
slave6OutputCurrentMaxCriticalThirtyseven OBJECT-TYPE
    SYNTAX      DisplayString
    MAX-ACCESS  read-write
    STATUS      current
    DESCRIPTION
	"The second output Max. current warning value of slave6"
    ::= { slave6OutputCurrentMaxCritical 37}
	
slave6OutputCurrentMaxCriticalThirtyeight OBJECT-TYPE
    SYNTAX      DisplayString
    MAX-ACCESS  read-write
    STATUS      current
    DESCRIPTION
	"The second output Max. current warning value of slave6"
    ::= { slave6OutputCurrentMaxCritical 38}
	
slave6OutputCurrentMaxCriticalThirtynine OBJECT-TYPE
    SYNTAX      DisplayString
    MAX-ACCESS  read-write
    STATUS      current
    DESCRIPTION
	"The second output Max. current warning value of slave6"
    ::= { slave6OutputCurrentMaxCritical 39}
	
slave6OutputCurrentMaxCriticalFourty OBJECT-TYPE
    SYNTAX      DisplayString
    MAX-ACCESS  read-write
    STATUS      current
    DESCRIPTION
	"The second output Max. current warning value of slave6"
    ::= { slave6OutputCurrentMaxCritical 40}
	
slave6OutputCurrentMaxCriticalFourtyone OBJECT-TYPE
    SYNTAX      DisplayString
    MAX-ACCESS  read-write
    STATUS      current
    DESCRIPTION
	"The second output Max. current warning value of slave6"
    ::= { slave6OutputCurrentMaxCritical 41}
	
slave6OutputCurrentMaxCriticalFourtytwo OBJECT-TYPE
    SYNTAX      DisplayString
    MAX-ACCESS  read-write
    STATUS      current
    DESCRIPTION
	"The second output Max. current warning value of slave6"
    ::= { slave6OutputCurrentMaxCritical 42}
	
	
------------------------slave6 output current Max----------------			
slave6OutputCurrentMax OBJECT IDENTIFIER ::= { slave6OutputCurrent 5}
	
slave6OutputCurrentMaxOne OBJECT-TYPE
    SYNTAX      DisplayString
    MAX-ACCESS  read-write
    STATUS      current
    DESCRIPTION
	"The first output Max. current alarm value of slave6"
    ::= { slave6OutputCurrentMax 1}

slave6OutputCurrentMaxTwo OBJECT-TYPE
    SYNTAX      DisplayString
    MAX-ACCESS  read-write
    STATUS      current
    DESCRIPTION
	"The second output Max. current alarm value of slave6"
    ::= { slave6OutputCurrentMax 2}

slave6OutputCurrentMaxThree OBJECT-TYPE
    SYNTAX      DisplayString
    MAX-ACCESS  read-write
    STATUS      current
    DESCRIPTION
	"The second output Max. current alarm value of slave6"
    ::= { slave6OutputCurrentMax 3}

slave6OutputCurrentMaxFour OBJECT-TYPE
    SYNTAX      DisplayString
    MAX-ACCESS  read-write
    STATUS      current
    DESCRIPTION
	"The second output Max. current alarm value of slave6"
    ::= { slave6OutputCurrentMax 4}

slave6OutputCurrentMaxFive OBJECT-TYPE
    SYNTAX      DisplayString
    MAX-ACCESS  read-write
    STATUS      current
    DESCRIPTION
	"The second output Max. current alarm value of slave6"
    ::= { slave6OutputCurrentMax 5}

slave6OutputCurrentMaxSix OBJECT-TYPE
    SYNTAX      DisplayString
    MAX-ACCESS  read-write
    STATUS      current
    DESCRIPTION
	"The second output Max. current alarm value of slave6"
    ::= { slave6OutputCurrentMax 6}

slave6OutputCurrentMaxSeven OBJECT-TYPE
    SYNTAX      DisplayString
    MAX-ACCESS  read-write
    STATUS      current
    DESCRIPTION
	"The second output Max. current alarm value of slave6"
    ::= { slave6OutputCurrentMax 7}

slave6OutputCurrentMaxEight OBJECT-TYPE
    SYNTAX      DisplayString
    MAX-ACCESS  read-write
    STATUS      current
    DESCRIPTION
	"The second output Max. current alarm value of slave6"
    ::= { slave6OutputCurrentMax 8}

slave6OutputCurrentMaxNine OBJECT-TYPE
    SYNTAX      DisplayString
    MAX-ACCESS  read-write
    STATUS      current
    DESCRIPTION
	"The second output Max. current alarm value of slave6"
    ::= { slave6OutputCurrentMax 9}

slave6OutputCurrentMaxTen OBJECT-TYPE
    SYNTAX      DisplayString
    MAX-ACCESS  read-write
    STATUS      current
    DESCRIPTION
	"The second output Max. current alarm value of slave6"
    ::= { slave6OutputCurrentMax 10}

slave6OutputCurrentMaxEleven OBJECT-TYPE
    SYNTAX      DisplayString
    MAX-ACCESS  read-write
    STATUS      current
    DESCRIPTION
	"The second output Max. current alarm value of slave6"
    ::= { slave6OutputCurrentMax 11}

slave6OutputCurrentMaxTwel OBJECT-TYPE
    SYNTAX      DisplayString
    MAX-ACCESS  read-write
    STATUS      current
    DESCRIPTION
	"The second output Max. current alarm value of slave6"
    ::= { slave6OutputCurrentMax 12}

slave6OutputCurrentMaxThirteen OBJECT-TYPE
    SYNTAX      DisplayString
    MAX-ACCESS  read-write
    STATUS      current
    DESCRIPTION
	"The second output Max. current alarm value of slave6"
    ::= { slave6OutputCurrentMax 13}

slave6OutputCurrentMaxFourteen OBJECT-TYPE
    SYNTAX      DisplayString
    MAX-ACCESS  read-write
    STATUS      current
    DESCRIPTION
	"The second output Max. current alarm value of slave6"
    ::= { slave6OutputCurrentMax 14}

slave6OutputCurrentMaxFifteen OBJECT-TYPE
    SYNTAX      DisplayString
    MAX-ACCESS  read-write
    STATUS      current
    DESCRIPTION
	"The second output Max. current alarm value of slave6"
    ::= { slave6OutputCurrentMax 15}

slave6OutputCurrentMaxSixteen OBJECT-TYPE
    SYNTAX      DisplayString
    MAX-ACCESS  read-write
    STATUS      current
    DESCRIPTION
	"The second output Max. current alarm value of slave6"
    ::= { slave6OutputCurrentMax 16}

slave6OutputCurrentMaxSeventeen OBJECT-TYPE
    SYNTAX      DisplayString
    MAX-ACCESS  read-write
    STATUS      current
    DESCRIPTION
	"The second output Max. current alarm value of slave6"
    ::= { slave6OutputCurrentMax 17}

slave6OutputCurrentMaxEighteen OBJECT-TYPE
    SYNTAX      DisplayString
    MAX-ACCESS  read-write
    STATUS      current
    DESCRIPTION
	"The second output Max. current alarm value of slave6"
    ::= { slave6OutputCurrentMax 18}
	
slave6OutputCurrentMaxNineteen OBJECT-TYPE
    SYNTAX      DisplayString
    MAX-ACCESS  read-write
    STATUS      current
    DESCRIPTION
	"The second output Max. current alarm value of slave6"
    ::= { slave6OutputCurrentMax 19}
	
slave6OutputCurrentMaxtwenty OBJECT-TYPE
    SYNTAX      DisplayString
    MAX-ACCESS  read-write
    STATUS      current
    DESCRIPTION
	"The second output Max. current alarm value of slave6"
    ::= { slave6OutputCurrentMax 20}
	
slave6OutputCurrentMaxTwentyone OBJECT-TYPE
    SYNTAX      DisplayString
    MAX-ACCESS  read-write
    STATUS      current
    DESCRIPTION
	"The second output Max. current alarm value of slave6"
    ::= { slave6OutputCurrentMax 21}
	
slave6OutputCurrentMaxTwentyonetwo OBJECT-TYPE
    SYNTAX      DisplayString
    MAX-ACCESS  read-write
    STATUS      current
    DESCRIPTION
	"The second output Max. current alarm value of slave6"
    ::= { slave6OutputCurrentMax 22}
	
slave6OutputCurrentMaxTwentythree OBJECT-TYPE
    SYNTAX      DisplayString
    MAX-ACCESS  read-write
    STATUS      current
    DESCRIPTION
	"The second output Max. current alarm value of slave6"
    ::= { slave6OutputCurrentMax 23}
	
slave6OutputCurrentMaxTwentyfour OBJECT-TYPE
    SYNTAX      DisplayString
    MAX-ACCESS  read-write
    STATUS      current
    DESCRIPTION
	"The second output Max. current alarm value of slave6"
    ::= { slave6OutputCurrentMax 24}
	
slave6OutputCurrentMaxTwentyfive OBJECT-TYPE
    SYNTAX      DisplayString
    MAX-ACCESS  read-write
    STATUS      current
    DESCRIPTION
	"The second output Max. current alarm value of slave6"
    ::= { slave6OutputCurrentMax 25}
	
slave6OutputCurrentMaxTwentysix OBJECT-TYPE
    SYNTAX      DisplayString
    MAX-ACCESS  read-write
    STATUS      current
    DESCRIPTION
	"The second output Max. current alarm value of slave6"
    ::= { slave6OutputCurrentMax 26}
	
slave6OutputCurrentMaxTwentyseven OBJECT-TYPE
    SYNTAX      DisplayString
    MAX-ACCESS  read-write
    STATUS      current
    DESCRIPTION
	"The second output Max. current alarm value of slave6"
    ::= { slave6OutputCurrentMax 27}
	
slave6OutputCurrentMaxTwentyeight OBJECT-TYPE
    SYNTAX      DisplayString
    MAX-ACCESS  read-write
    STATUS      current
    DESCRIPTION
	"The second output Max. current alarm value of slave6"
    ::= { slave6OutputCurrentMax 28}	
slave6OutputCurrentMaxTwentynine OBJECT-TYPE
    SYNTAX      DisplayString
    MAX-ACCESS  read-write
    STATUS      current
    DESCRIPTION
	"The second output Max. current alarm value of slave6"
    ::= { slave6OutputCurrentMax 29}
	
slave6OutputCurrentMaxThirty OBJECT-TYPE
    SYNTAX      DisplayString
    MAX-ACCESS  read-write
    STATUS      current
    DESCRIPTION
	"The second output Max. current alarm value of slave6"
    ::= { slave6OutputCurrentMax 30}
	
slave6OutputCurrentMaxThirtyone OBJECT-TYPE
    SYNTAX      DisplayString
    MAX-ACCESS  read-write
    STATUS      current
    DESCRIPTION
	"The second output Max. current alarm value of slave6"
    ::= { slave6OutputCurrentMax 31}
	
slave6OutputCurrentMaxThirtytwo OBJECT-TYPE
    SYNTAX      DisplayString
    MAX-ACCESS  read-write
    STATUS      current
    DESCRIPTION
	"The second output Max. current alarm value of slave6"
    ::= { slave6OutputCurrentMax 32}
	
slave6OutputCurrentMaxThirtythree OBJECT-TYPE
    SYNTAX      DisplayString
    MAX-ACCESS  read-write
    STATUS      current
    DESCRIPTION
	"The second output Max. current alarm value of slave6"
    ::= { slave6OutputCurrentMax 33}
	
slave6OutputCurrentMaxThirtyfour OBJECT-TYPE
    SYNTAX      DisplayString
    MAX-ACCESS  read-write
    STATUS      current
    DESCRIPTION
	"The second output Max. current alarm value of slave6"
    ::= { slave6OutputCurrentMax 34}
	
slave6OutputCurrentMaxThirtyfive OBJECT-TYPE
    SYNTAX      DisplayString
    MAX-ACCESS  read-write
    STATUS      current
    DESCRIPTION
	"The second output Max. current alarm value of slave6"
    ::= { slave6OutputCurrentMax 35}
	
slave6OutputCurrentMaxThirtysix OBJECT-TYPE
    SYNTAX      DisplayString
    MAX-ACCESS  read-write
    STATUS      current
    DESCRIPTION
	"The second output Max. current alarm value of slave6"
    ::= { slave6OutputCurrentMax 36}
	
slave6OutputCurrentMaxThirtyseven OBJECT-TYPE
    SYNTAX      DisplayString
    MAX-ACCESS  read-write
    STATUS      current
    DESCRIPTION
	"The second output Max. current alarm value of slave6"
    ::= { slave6OutputCurrentMax 37}
	
slave6OutputCurrentMaxThirtyeight OBJECT-TYPE
    SYNTAX      DisplayString
    MAX-ACCESS  read-write
    STATUS      current
    DESCRIPTION
	"The second output Max. current alarm value of slave6"
    ::= { slave6OutputCurrentMax 38}
	
slave6OutputCurrentMaxThirtynine OBJECT-TYPE
    SYNTAX      DisplayString
    MAX-ACCESS  read-write
    STATUS      current
    DESCRIPTION
	"The second output Max. current alarm value of slave6"
    ::= { slave6OutputCurrentMax 39}
	
slave6OutputCurrentMaxFourty OBJECT-TYPE
    SYNTAX      DisplayString
    MAX-ACCESS  read-write
    STATUS      current
    DESCRIPTION
	"The second output Max. current alarm value of slave6"
    ::= { slave6OutputCurrentMax 40}
	
slave6OutputCurrentMaxFourtyone OBJECT-TYPE
    SYNTAX      DisplayString
    MAX-ACCESS  read-write
    STATUS      current
    DESCRIPTION
	"The second output Max. current alarm value of slave6"
    ::= { slave6OutputCurrentMax 41}
	
slave6OutputCurrentMaxFourtytwo OBJECT-TYPE
    SYNTAX      DisplayString
    MAX-ACCESS  read-write
    STATUS      current
    DESCRIPTION
	"The second output Max. current alarm value of slave6"
    ::= { slave6OutputCurrentMax 42}
	
	
-------------------------------slave6 output powerfactor------------------------	
slave6OutputPowerfactor OBJECT IDENTIFIER ::= { slave6 9}	

slave6OutputPowerfactorOne OBJECT-TYPE
    SYNTAX      DisplayString
    MAX-ACCESS  read-only
    STATUS      current
    DESCRIPTION
	"The ouput power factor of slave6." 
	::= { slave6OutputPowerfactor 1}

slave6OutputPowerfactorTwo OBJECT-TYPE
    SYNTAX      DisplayString
    MAX-ACCESS  read-only
    STATUS      current
    DESCRIPTION
	"The ouput power factor of slave6." 
	::= { slave6OutputPowerfactor 2}
	
slave6OutputPowerfactorThree OBJECT-TYPE
    SYNTAX      DisplayString
    MAX-ACCESS  read-only
    STATUS      current
    DESCRIPTION
	"The ouput power factor of slave6." 
	::= { slave6OutputPowerfactor 3}
	
slave6OutputPowerfactorFour OBJECT-TYPE
    SYNTAX      DisplayString
    MAX-ACCESS  read-only
    STATUS      current
    DESCRIPTION
	"The ouput power factor of slave6." 
	::= { slave6OutputPowerfactor 4}
		
slave6OutputPowerfactorFive OBJECT-TYPE
    SYNTAX      DisplayString
    MAX-ACCESS  read-only
    STATUS      current
    DESCRIPTION
	"The ouput power factor of slave6." 
	::= { slave6OutputPowerfactor 5}
	
slave6OutputPowerfactorSix OBJECT-TYPE
    SYNTAX      DisplayString
    MAX-ACCESS  read-only
    STATUS      current
    DESCRIPTION
	"The ouput power factor of slave6." 
	::= { slave6OutputPowerfactor 6}
	
slave6OutputPowerfactorSeven OBJECT-TYPE
    SYNTAX      DisplayString
    MAX-ACCESS  read-only
    STATUS      current
    DESCRIPTION
	"The ouput power factor of slave6." 
	::= { slave6OutputPowerfactor 7}	
	
slave6OutputPowerfactorEight OBJECT-TYPE
    SYNTAX      DisplayString
    MAX-ACCESS  read-only
    STATUS      current
    DESCRIPTION
	"The ouput power factor of slave6." 
	::= { slave6OutputPowerfactor 8}
	
slave6OutputPowerfactorNine OBJECT-TYPE
    SYNTAX      DisplayString
    MAX-ACCESS  read-only
    STATUS      current
    DESCRIPTION
	"The ouput power factor of slave6." 
	::= { slave6OutputPowerfactor 9}
		
slave6OutputPowerfactorTen OBJECT-TYPE
    SYNTAX      DisplayString
    MAX-ACCESS  read-only
    STATUS      current
    DESCRIPTION
	"The ouput power factor of slave6." 
	::= { slave6OutputPowerfactor 10}
		
slave6OutputPowerfactorEleven OBJECT-TYPE
    SYNTAX      DisplayString
    MAX-ACCESS  read-only
    STATUS      current
    DESCRIPTION
	"The ouput power factor of slave6." 
	::= { slave6OutputPowerfactor 11}
		
slave6OutputPowerfactorTwel OBJECT-TYPE
    SYNTAX      DisplayString
    MAX-ACCESS  read-only
    STATUS      current
    DESCRIPTION
	"The ouput power factor of slave6." 
	::= { slave6OutputPowerfactor 12}
		
slave6OutputPowerfactorThirteen OBJECT-TYPE
    SYNTAX      DisplayString
    MAX-ACCESS  read-only
    STATUS      current
    DESCRIPTION
	"The ouput power factor of slave6." 
	::= { slave6OutputPowerfactor 13}
		
slave6OutputPowerfactorFourteen OBJECT-TYPE
    SYNTAX      DisplayString
    MAX-ACCESS  read-only
    STATUS      current
    DESCRIPTION
	"The ouput power factor of slave6." 
	::= { slave6OutputPowerfactor 14}
		
slave6OutputPowerfactorFifteen OBJECT-TYPE
    SYNTAX      DisplayString
    MAX-ACCESS  read-only
    STATUS      current
    DESCRIPTION
	"The ouput power factor of slave6." 
	::= { slave6OutputPowerfactor 15}
		
slave6OutputPowerfactorSixteen OBJECT-TYPE
    SYNTAX      DisplayString
    MAX-ACCESS  read-only
    STATUS      current
    DESCRIPTION
	"The ouput power factor of slave6." 
	::= { slave6OutputPowerfactor 16}
		
slave6OutputPowerfactorSeventeen OBJECT-TYPE
    SYNTAX      DisplayString
    MAX-ACCESS  read-only
    STATUS      current
    DESCRIPTION
	"The ouput power factor of slave6." 
	::= { slave6OutputPowerfactor 17}
		
slave6OutputPowerfactorEighteen OBJECT-TYPE
    SYNTAX      DisplayString
    MAX-ACCESS  read-only
    STATUS      current
    DESCRIPTION
	"The ouput power factor of slave6." 
	::= { slave6OutputPowerfactor 18}
		
slave6OutputPowerfactorNineteen OBJECT-TYPE
    SYNTAX      DisplayString
    MAX-ACCESS  read-only
    STATUS      current
    DESCRIPTION
	"The ouput power factor of slave6." 
	::= { slave6OutputPowerfactor 19}
		
slave6OutputPowerfactorTwenty OBJECT-TYPE
    SYNTAX      DisplayString
    MAX-ACCESS  read-only
    STATUS      current
    DESCRIPTION
	"The ouput power factor of slave6." 
	::= { slave6OutputPowerfactor 20}
		
slave6OutputPowerfactorTwentyone OBJECT-TYPE
    SYNTAX      DisplayString
    MAX-ACCESS  read-only
    STATUS      current
    DESCRIPTION
	"The ouput power factor of slave6." 
	::= { slave6OutputPowerfactor 21}
		
slave6OutputPowerfactorTwentytwo OBJECT-TYPE
    SYNTAX      DisplayString
    MAX-ACCESS  read-only
    STATUS      current
    DESCRIPTION
	"The ouput power factor of slave6." 
	::= { slave6OutputPowerfactor 22}
		
slave6OutputPowerfactorTwentythree OBJECT-TYPE
    SYNTAX      DisplayString
    MAX-ACCESS  read-only
    STATUS      current
    DESCRIPTION
	"The ouput power factor of slave6." 
	::= { slave6OutputPowerfactor 23}
		
slave6OutputPowerfactorTwentyfour OBJECT-TYPE
    SYNTAX      DisplayString
    MAX-ACCESS  read-only
    STATUS      current
    DESCRIPTION
	"The ouput power factor of slave6." 
	::= { slave6OutputPowerfactor 24}
		
slave6OutputPowerfactorTwentyfive OBJECT-TYPE
    SYNTAX      DisplayString
    MAX-ACCESS  read-only
    STATUS      current
    DESCRIPTION
	"The ouput power factor of slave6." 
	::= { slave6OutputPowerfactor 25}
		
slave6OutputPowerfactorTwentysix OBJECT-TYPE
    SYNTAX      DisplayString
    MAX-ACCESS  read-only
    STATUS      current
    DESCRIPTION
	"The ouput power factor of slave6." 
	::= { slave6OutputPowerfactor 26}
		
slave6OutputPowerfactorTwentyseven OBJECT-TYPE
    SYNTAX      DisplayString
    MAX-ACCESS  read-only
    STATUS      current
    DESCRIPTION
	"The ouput power factor of slave6." 
	::= { slave6OutputPowerfactor 27}
		
slave6OutputPowerfactorTwentyeight OBJECT-TYPE
    SYNTAX      DisplayString
    MAX-ACCESS  read-only
    STATUS      current
    DESCRIPTION
	"The ouput power factor of slave6." 
	::= { slave6OutputPowerfactor 28}
		
slave6OutputPowerfactorTwentynine OBJECT-TYPE
    SYNTAX      DisplayString
    MAX-ACCESS  read-only
    STATUS      current
    DESCRIPTION
	"The ouput power factor of slave6." 
	::= { slave6OutputPowerfactor 29}
		
slave6OutputPowerfactorThirty OBJECT-TYPE
    SYNTAX      DisplayString
    MAX-ACCESS  read-only
    STATUS      current
    DESCRIPTION
	"The ouput power factor of slave6." 
	::= { slave6OutputPowerfactor 30}
		
slave6OutputPowerfactorThirtyone OBJECT-TYPE
    SYNTAX      DisplayString
    MAX-ACCESS  read-only
    STATUS      current
    DESCRIPTION
	"The ouput power factor of slave6." 
	::= { slave6OutputPowerfactor 31}
		
slave6OutputPowerfactorThirtytwo OBJECT-TYPE
    SYNTAX      DisplayString
    MAX-ACCESS  read-only
    STATUS      current
    DESCRIPTION
	"The ouput power factor of slave6." 
	::= { slave6OutputPowerfactor 32}
		
slave6OutputPowerfactorThirtythree OBJECT-TYPE
    SYNTAX      DisplayString
    MAX-ACCESS  read-only
    STATUS      current
    DESCRIPTION
	"The ouput power factor of slave6." 
	::= { slave6OutputPowerfactor 33}	
	
slave6OutputPowerfactorThirtyfour OBJECT-TYPE
    SYNTAX      DisplayString
    MAX-ACCESS  read-only
    STATUS      current
    DESCRIPTION
	"The ouput power factor of slave6." 
	::= { slave6OutputPowerfactor 34}
	
	
slave6OutputPowerfactorThirtyfive OBJECT-TYPE
    SYNTAX      DisplayString
    MAX-ACCESS  read-only
    STATUS      current
    DESCRIPTION
	"The ouput power factor of slave6." 
	::= { slave6OutputPowerfactor 35}
		
slave6OutputPowerfactorThirtysix OBJECT-TYPE
    SYNTAX      DisplayString
    MAX-ACCESS  read-only
    STATUS      current
    DESCRIPTION
	"The ouput power factor of slave6." 
	::= { slave6OutputPowerfactor 36}
		
slave6OutputPowerfactorThirtyseven OBJECT-TYPE
    SYNTAX      DisplayString
    MAX-ACCESS  read-only
    STATUS      current
    DESCRIPTION
	"The ouput power factor of slave6." 
	::= { slave6OutputPowerfactor 37}
		
slave6OutputPowerfactorThirtyeight OBJECT-TYPE
    SYNTAX      DisplayString
    MAX-ACCESS  read-only
    STATUS      current
    DESCRIPTION
	"The ouput power factor of slave6." 
	::= { slave6OutputPowerfactor 38}
		
slave6OutputPowerfactorThirtynine OBJECT-TYPE
    SYNTAX      DisplayString
    MAX-ACCESS  read-only
    STATUS      current
    DESCRIPTION
	"The ouput power factor of slave6." 
	::= { slave6OutputPowerfactor 39}
		
slave6OutputPowerfactorFourty OBJECT-TYPE
    SYNTAX      DisplayString
    MAX-ACCESS  read-only
    STATUS      current
    DESCRIPTION
	"The ouput power factor of slave6." 
	::= { slave6OutputPowerfactor 40}
		
slave6OutputPowerfactorFourtyone OBJECT-TYPE
    SYNTAX      DisplayString
    MAX-ACCESS  read-only
    STATUS      current
    DESCRIPTION
	"The ouput power factor of slave6." 
	::= { slave6OutputPowerfactor 41}
		
slave6OutputPowerfactorFourtytwo OBJECT-TYPE
    SYNTAX      DisplayString
    MAX-ACCESS  read-only
    STATUS      current
    DESCRIPTION
	"The ouput power factor of slave6." 
	::= { slave6OutputPowerfactor 42}	
	
-------------------------------slave6 output energy------------------------	
slave6OutputEnergy OBJECT IDENTIFIER ::= { slave6 10}

slave6OutputEnergyOne OBJECT-TYPE
    SYNTAX      DisplayString
    MAX-ACCESS  read-only
    STATUS      current
    DESCRIPTION
	"The ouput power of slave6." 
	::= { slave6OutputEnergy 1}

slave6OutputEnergyTwo OBJECT-TYPE
    SYNTAX      DisplayString
    MAX-ACCESS  read-only
    STATUS      current
    DESCRIPTION
	"The ouput power of slave6." 
	::= { slave6OutputEnergy 2}
	
slave6OutputEnergyThree OBJECT-TYPE
    SYNTAX      DisplayString
    MAX-ACCESS  read-only
    STATUS      current
    DESCRIPTION
	"The ouput power of slave6." 
	::= { slave6OutputEnergy 3}
	
slave6OutputEnergyFour OBJECT-TYPE
    SYNTAX      DisplayString
    MAX-ACCESS  read-only
    STATUS      current
    DESCRIPTION
	"The ouput power of slave6." 
	::= { slave6OutputEnergy 4}
		
slave6OutputEnergyFive OBJECT-TYPE
    SYNTAX      DisplayString
    MAX-ACCESS  read-only
    STATUS      current
    DESCRIPTION
	"The ouput power of slave6." 
	::= { slave6OutputEnergy 5}
	
slave6OutputEnergySix OBJECT-TYPE
    SYNTAX      DisplayString
    MAX-ACCESS  read-only
    STATUS      current
    DESCRIPTION
	"The ouput power of slave6." 
	::= { slave6OutputEnergy 6}
	
slave6OutputEnergySeven OBJECT-TYPE
    SYNTAX      DisplayString
    MAX-ACCESS  read-only
    STATUS      current
    DESCRIPTION
	"The ouput power of slave6." 
	::= { slave6OutputEnergy 7}	
	
slave6OutputEnergyEight OBJECT-TYPE
    SYNTAX      DisplayString
    MAX-ACCESS  read-only
    STATUS      current
    DESCRIPTION
	"The ouput power of slave6." 
	::= { slave6OutputEnergy 8}
	
slave6OutputEnergyNine OBJECT-TYPE
    SYNTAX      DisplayString
    MAX-ACCESS  read-only
    STATUS      current
    DESCRIPTION
	"The ouput power of slave6." 
	::= { slave6OutputEnergy 9}
		
slave6OutputEnergyTen OBJECT-TYPE
    SYNTAX      DisplayString
    MAX-ACCESS  read-only
    STATUS      current
    DESCRIPTION
	"The ouput power of slave6." 
	::= { slave6OutputEnergy 10}
		
slave6OutputEnergyEleven OBJECT-TYPE
    SYNTAX      DisplayString
    MAX-ACCESS  read-only
    STATUS      current
    DESCRIPTION
	"The ouput power of slave6." 
	::= { slave6OutputEnergy 11}
		
slave6OutputEnergyTwel OBJECT-TYPE
    SYNTAX      DisplayString
    MAX-ACCESS  read-only
    STATUS      current
    DESCRIPTION
	"The ouput power of slave6." 
	::= { slave6OutputEnergy 12}
		
slave6OutputEnergyThirteen OBJECT-TYPE
    SYNTAX      DisplayString
    MAX-ACCESS  read-only
    STATUS      current
    DESCRIPTION
	"The ouput power of slave6." 
	::= { slave6OutputEnergy 13}
		
slave6OutputEnergyFourteen OBJECT-TYPE
    SYNTAX      DisplayString
    MAX-ACCESS  read-only
    STATUS      current
    DESCRIPTION
	"The ouput power of slave6." 
	::= { slave6OutputEnergy 14}
		
slave6OutputEnergyFifteen OBJECT-TYPE
    SYNTAX      DisplayString
    MAX-ACCESS  read-only
    STATUS      current
    DESCRIPTION
	"The ouput power of slave6." 
	::= { slave6OutputEnergy 15}
		
slave6OutputEnergySixteen OBJECT-TYPE
    SYNTAX      DisplayString
    MAX-ACCESS  read-only
    STATUS      current
    DESCRIPTION
	"The ouput power of slave6." 
	::= { slave6OutputEnergy 16}
		
slave6OutputEnergySeventeen OBJECT-TYPE
    SYNTAX      DisplayString
    MAX-ACCESS  read-only
    STATUS      current
    DESCRIPTION
	"The ouput power of slave6." 
	::= { slave6OutputEnergy 17}
		
slave6OutputEnergyEighteen OBJECT-TYPE
    SYNTAX      DisplayString
    MAX-ACCESS  read-only
    STATUS      current
    DESCRIPTION
	"The ouput power of slave6." 
	::= { slave6OutputEnergy 18}
		
slave6OutputEnergyNineteen OBJECT-TYPE
    SYNTAX      DisplayString
    MAX-ACCESS  read-only
    STATUS      current
    DESCRIPTION
	"The ouput power of slave6." 
	::= { slave6OutputEnergy 19}
		
slave6OutputEnergyTwenty OBJECT-TYPE
    SYNTAX      DisplayString
    MAX-ACCESS  read-only
    STATUS      current
    DESCRIPTION
	"The ouput power of slave6." 
	::= { slave6OutputEnergy 20}
		
slave6OutputEnergyTwentyone OBJECT-TYPE
    SYNTAX      DisplayString
    MAX-ACCESS  read-only
    STATUS      current
    DESCRIPTION
	"The ouput power of slave6." 
	::= { slave6OutputEnergy 21}
		
slave6OutputEnergyTwentytwo OBJECT-TYPE
    SYNTAX      DisplayString
    MAX-ACCESS  read-only
    STATUS      current
    DESCRIPTION
	"The ouput power of slave6." 
	::= { slave6OutputEnergy 22}
		
slave6OutputEnergyTwentythree OBJECT-TYPE
    SYNTAX      DisplayString
    MAX-ACCESS  read-only
    STATUS      current
    DESCRIPTION
	"The ouput power of slave6." 
	::= { slave6OutputEnergy 23}
		
slave6OutputEnergyTwentyfour OBJECT-TYPE
    SYNTAX      DisplayString
    MAX-ACCESS  read-only
    STATUS      current
    DESCRIPTION
	"The ouput power of slave6." 
	::= { slave6OutputEnergy 24}
		
slave6OutputEnergyTwentyfive OBJECT-TYPE
    SYNTAX      DisplayString
    MAX-ACCESS  read-only
    STATUS      current
    DESCRIPTION
	"The ouput power of slave6." 
	::= { slave6OutputEnergy 25}
		
slave6OutputEnergyTwentysix OBJECT-TYPE
    SYNTAX      DisplayString
    MAX-ACCESS  read-only
    STATUS      current
    DESCRIPTION
	"The ouput power of slave6." 
	::= { slave6OutputEnergy 26}
		
slave6OutputEnergyTwentyseven OBJECT-TYPE
    SYNTAX      DisplayString
    MAX-ACCESS  read-only
    STATUS      current
    DESCRIPTION
	"The ouput power of slave6." 
	::= { slave6OutputEnergy 27}
		
slave6OutputEnergyTwentyeight OBJECT-TYPE
    SYNTAX      DisplayString
    MAX-ACCESS  read-only
    STATUS      current
    DESCRIPTION
	"The ouput power of slave6." 
	::= { slave6OutputEnergy 28}
		
slave6OutputEnergyTwentynine OBJECT-TYPE
    SYNTAX      DisplayString
    MAX-ACCESS  read-only
    STATUS      current
    DESCRIPTION
	"The ouput power of slave6." 
	::= { slave6OutputEnergy 29}
		
slave6OutputEnergyThirty OBJECT-TYPE
    SYNTAX      DisplayString
    MAX-ACCESS  read-only
    STATUS      current
    DESCRIPTION
	"The ouput power of slave6." 
	::= { slave6OutputEnergy 30}
		
slave6OutputEnergyThirtyone OBJECT-TYPE
    SYNTAX      DisplayString
    MAX-ACCESS  read-only
    STATUS      current
    DESCRIPTION
	"The ouput power of slave6." 
	::= { slave6OutputEnergy 31}
		
slave6OutputEnergyThirtytwo OBJECT-TYPE
    SYNTAX      DisplayString
    MAX-ACCESS  read-only
    STATUS      current
    DESCRIPTION
	"The ouput power of slave6." 
	::= { slave6OutputEnergy 32}
		
slave6OutputEnergyThirtythree OBJECT-TYPE
    SYNTAX      DisplayString
    MAX-ACCESS  read-only
    STATUS      current
    DESCRIPTION
	"The ouput power of slave6." 
	::= { slave6OutputEnergy 33}	
	
slave6OutputEnergyThirtyfour OBJECT-TYPE
    SYNTAX      DisplayString
    MAX-ACCESS  read-only
    STATUS      current
    DESCRIPTION
	"The ouput power of slave6." 
	::= { slave6OutputEnergy 34}
	
	
slave6OutputEnergyThirtyfive OBJECT-TYPE
    SYNTAX      DisplayString
    MAX-ACCESS  read-only
    STATUS      current
    DESCRIPTION
	"The ouput power of slave6." 
	::= { slave6OutputEnergy 35}
		
slave6OutputEnergyThirtysix OBJECT-TYPE
    SYNTAX      DisplayString
    MAX-ACCESS  read-only
    STATUS      current
    DESCRIPTION
	"The ouput power of slave6." 
	::= { slave6OutputEnergy 36}
		
slave6OutputEnergyThirtyseven OBJECT-TYPE
    SYNTAX      DisplayString
    MAX-ACCESS  read-only
    STATUS      current
    DESCRIPTION
	"The ouput power of slave6." 
	::= { slave6OutputEnergy 37}
		
slave6OutputEnergyThirtyeight OBJECT-TYPE
    SYNTAX      DisplayString
    MAX-ACCESS  read-only
    STATUS      current
    DESCRIPTION
	"The ouput power of slave6." 
	::= { slave6OutputEnergy 38}
		
slave6OutputEnergyThirtynine OBJECT-TYPE
    SYNTAX      DisplayString
    MAX-ACCESS  read-only
    STATUS      current
    DESCRIPTION
	"The ouput power of slave6." 
	::= { slave6OutputEnergy 39}
		
slave6OutputEnergyFourty OBJECT-TYPE
    SYNTAX      DisplayString
    MAX-ACCESS  read-only
    STATUS      current
    DESCRIPTION
	"The ouput power of slave6." 
	::= { slave6OutputEnergy 40}
		
slave6OutputEnergyFourtyone OBJECT-TYPE
    SYNTAX      DisplayString
    MAX-ACCESS  read-only
    STATUS      current
    DESCRIPTION
	"The ouput power of slave6." 
	::= { slave6OutputEnergy 41}
		
slave6OutputEnergyFourtytwo OBJECT-TYPE
    SYNTAX      DisplayString
    MAX-ACCESS  read-only
    STATUS      current
    DESCRIPTION
	"The ouput power of slave6." 
	::= { slave6OutputEnergy 42}	

	
	
	
	
-------------------------------slave7 information--------------------
slave7 OBJECT IDENTIFIER ::= { pdu 8}
slave7Information OBJECT IDENTIFIER ::= { slave7 1}
slave7Name OBJECT-TYPE
    SYNTAX      DisplayString
    MAX-ACCESS  read-write
    STATUS      current
    DESCRIPTION
	"This is the first device."
    ::= { slave7Information 1}
    
slave7Type OBJECT-TYPE
    SYNTAX      DisplayString
    MAX-ACCESS  read-only
    STATUS      current
    DESCRIPTION
	"This is device type "
    ::= { slave7Information 2}
    
slave7OutputNumber OBJECT-TYPE 
    SYNTAX      Integer32
    MAX-ACCESS  read-only
    STATUS      current
    DESCRIPTION
	"This is the number of output bits"
	::= { slave7Information 3}
	
slave7MacAdress OBJECT-TYPE
    SYNTAX      DisplayString
    MAX-ACCESS  read-only
    STATUS      current
    DESCRIPTION
	"This is device MAC adress"
    ::= { slave7Information 4}	

slave7Vison OBJECT-TYPE
    SYNTAX      DisplayString
    MAX-ACCESS  read-only
    STATUS      current
    DESCRIPTION
	"This is device vison "
    ::= { slave7Information 5}

slave7Frequency OBJECT-TYPE
    SYNTAX      Integer32
    MAX-ACCESS  read-only
    STATUS      current
    DESCRIPTION
	"This is device frequency "
    ::= { slave7Information 6}
	
slave7Emission OBJECT-TYPE
    SYNTAX      DisplayString
    MAX-ACCESS  read-only
    STATUS      current
    DESCRIPTION
	"This is device emission "
    ::= { slave7Information 7}	
	
slave7RunTime OBJECT-TYPE
    SYNTAX      DisplayString
    MAX-ACCESS  read-only
    STATUS      current
    DESCRIPTION
	"This is device running time "
    ::= { slave7Information 8}	

slave7BuzzerSwitch OBJECT-TYPE
    SYNTAX      DisplayString
    MAX-ACCESS  read-write
    STATUS      current
    DESCRIPTION
	"This is device buzzer switch."
    ::= { slave7Information 9}	

	
-------------------------------slave7 phase--------------------
slave7Phase OBJECT IDENTIFIER ::= { slave7 2}	
	
slave7PhaseOne OBJECT IDENTIFIER ::= { slave7Phase 1}	    
slave7PhaseOneCurrent OBJECT-TYPE
    SYNTAX      DisplayString
    MAX-ACCESS  read-only
    STATUS      current
    DESCRIPTION
	"The power of phase one"
    ::= { slave7PhaseOne 1}

slave7PhaseOneVoltage OBJECT-TYPE
    SYNTAX      DisplayString
    MAX-ACCESS  read-only
    STATUS      current
    DESCRIPTION
	"The power of phase one"
    ::= { slave7PhaseOne 2}

slave7PhaseOnePower OBJECT-TYPE
    SYNTAX      DisplayString
    MAX-ACCESS  read-only
    STATUS      current
    DESCRIPTION
	"The power of phase one"
    ::= { slave7PhaseOne 3}
	
slave7PhaseOnePowerfactor OBJECT-TYPE
    SYNTAX      DisplayString
    MAX-ACCESS  read-only
    STATUS      current
    DESCRIPTION
	"The power of phase one"
    ::= { slave7PhaseOne 4}	
	
slave7PhaseOneEnergy OBJECT-TYPE
    SYNTAX      DisplayString
    MAX-ACCESS  read-only
    STATUS      current
    DESCRIPTION
	"The power of phase one"
    ::= { slave7PhaseOne 5}	
		
slave7PhaseOneCurrentMin OBJECT-TYPE
    SYNTAX      DisplayString
    MAX-ACCESS  read-write
    STATUS      current
    DESCRIPTION
	"The power of phase one"
    ::= { slave7PhaseOne 6}	
	
slave7PhaseOneCurrentMinCritical OBJECT-TYPE
    SYNTAX      DisplayString
    MAX-ACCESS  read-write
    STATUS      current
    DESCRIPTION
	"The power of phase one"
    ::= { slave7PhaseOne 7}
	
slave7PhaseOneCurrentMaxCritical OBJECT-TYPE
    SYNTAX      DisplayString
    MAX-ACCESS  read-write
    STATUS      current
    DESCRIPTION
	"The power of phase one"
    ::= { slave7PhaseOne 8}
	
slave7PhaseOneCurrentMax OBJECT-TYPE
    SYNTAX      DisplayString
    MAX-ACCESS  read-write
    STATUS      current
    DESCRIPTION
	"The power of phase one"
    ::= { slave7PhaseOne 9}
	
slave7PhaseOneVoltageMin OBJECT-TYPE
    SYNTAX      DisplayString
    MAX-ACCESS  read-write
    STATUS      current
    DESCRIPTION
	"The power of phase one"
    ::= { slave7PhaseOne 10}
	
slave7PhaseOneVoltageMinCritical OBJECT-TYPE
    SYNTAX      DisplayString
    MAX-ACCESS  read-write
    STATUS      current
    DESCRIPTION
	"The power of phase one"
    ::= { slave7PhaseOne 11}

slave7PhaseOneVoltageMaxCritical OBJECT-TYPE
    SYNTAX      DisplayString
    MAX-ACCESS  read-write
    STATUS      current
    DESCRIPTION
	"The power of phase one"
    ::= { slave7PhaseOne 12}
	
slave7PhaseOneVoltageMax OBJECT-TYPE
    SYNTAX      DisplayString
    MAX-ACCESS  read-write
    STATUS      current
    DESCRIPTION
	"The power of phase one"
    ::= { slave7PhaseOne 13}


slave7PhaseTwo OBJECT IDENTIFIER ::= { slave7Phase 2}	    
slave7PhaseTwoCurrent OBJECT-TYPE
    SYNTAX      DisplayString
    MAX-ACCESS  read-only
    STATUS      current
    DESCRIPTION
	"The power of phase one"
    ::= { slave7PhaseTwo 1}

slave7PhaseTwoVoltage OBJECT-TYPE
    SYNTAX      DisplayString
    MAX-ACCESS  read-only
    STATUS      current
    DESCRIPTION
	"The power of phase one"
    ::= { slave7PhaseTwo 2}

slave7PhaseTwoPower OBJECT-TYPE
    SYNTAX      DisplayString
    MAX-ACCESS  read-only
    STATUS      current
    DESCRIPTION
	"The power of phase one"
    ::= { slave7PhaseTwo 3}
	
slave7PhaseTwoPowerfactor OBJECT-TYPE
    SYNTAX      DisplayString
    MAX-ACCESS  read-only
    STATUS      current
    DESCRIPTION
	"The power of phase one"
    ::= { slave7PhaseTwo 4}	
	
slave7PhaseTwoEnergy OBJECT-TYPE
    SYNTAX      DisplayString
    MAX-ACCESS  read-only
    STATUS      current
    DESCRIPTION
	"The power of phase one"
    ::= { slave7PhaseTwo 5}	
		
slave7PhaseTwoCurrentMin OBJECT-TYPE
    SYNTAX      DisplayString
    MAX-ACCESS  read-write
    STATUS      current
    DESCRIPTION
	"The power of phase one"
    ::= { slave7PhaseTwo 6}	
	
slave7PhaseTwoCurrentMinCritical OBJECT-TYPE
    SYNTAX      DisplayString
    MAX-ACCESS  read-write
    STATUS      current
    DESCRIPTION
	"The power of phase one"
    ::= { slave7PhaseTwo 7}
	
slave7PhaseTwoCurrentMaxCritical OBJECT-TYPE
    SYNTAX      DisplayString
    MAX-ACCESS  read-write
    STATUS      current
    DESCRIPTION
	"The power of phase one"
    ::= { slave7PhaseTwo 8}
	
slave7PhaseTwoCurrentMax OBJECT-TYPE
    SYNTAX      DisplayString
    MAX-ACCESS  read-write
    STATUS      current
    DESCRIPTION
	"The power of phase one"
    ::= { slave7PhaseTwo 9}
	
slave7PhaseTwoVoltageMin OBJECT-TYPE
    SYNTAX      DisplayString
    MAX-ACCESS  read-write
    STATUS      current
    DESCRIPTION
	"The power of phase one"
    ::= { slave7PhaseTwo 10}
	
slave7PhaseTwoVoltageMinCritical OBJECT-TYPE
    SYNTAX      DisplayString
    MAX-ACCESS  read-write
    STATUS      current
    DESCRIPTION
	"The power of phase one"
    ::= { slave7PhaseTwo 11}

slave7PhaseTwoVoltageMaxCritical OBJECT-TYPE
    SYNTAX      DisplayString
    MAX-ACCESS  read-write
    STATUS      current
    DESCRIPTION
	"The power of phase one"
    ::= { slave7PhaseTwo 12}
	
slave7PhaseTwoVoltageMax OBJECT-TYPE
    SYNTAX      DisplayString
    MAX-ACCESS  read-write
    STATUS      current
    DESCRIPTION
	"The power of phase one"
    ::= { slave7PhaseTwo 13}
	
	
slave7PhaseThree OBJECT IDENTIFIER ::= { slave7Phase 3}	    
slave7PhaseThreeCurrent OBJECT-TYPE
    SYNTAX      DisplayString
    MAX-ACCESS  read-only
    STATUS      current
    DESCRIPTION
	"The power of phase one"
    ::= { slave7PhaseThree 1}

slave7PhaseThreeVoltage OBJECT-TYPE
    SYNTAX      DisplayString
    MAX-ACCESS  read-only
    STATUS      current
    DESCRIPTION
	"The power of phase one"
    ::= { slave7PhaseThree 2}

slave7PhaseThreePower OBJECT-TYPE
    SYNTAX      DisplayString
    MAX-ACCESS  read-only
    STATUS      current
    DESCRIPTION
	"The power of phase one"
    ::= { slave7PhaseThree 3}
	
slave7PhaseThreePowerfactor OBJECT-TYPE
    SYNTAX      DisplayString
    MAX-ACCESS  read-only
    STATUS      current
    DESCRIPTION
	"The power of phase one"
    ::= { slave7PhaseThree 4}	
	
slave7PhaseThreeEnergy OBJECT-TYPE
    SYNTAX      DisplayString
    MAX-ACCESS  read-only
    STATUS      current
    DESCRIPTION
	"The power of phase one"
    ::= { slave7PhaseThree 5}	
		
slave7PhaseThreeCurrentMin OBJECT-TYPE
    SYNTAX      DisplayString
    MAX-ACCESS  read-write
    STATUS      current
    DESCRIPTION
	"The power of phase one"
    ::= { slave7PhaseThree 6}	
	
slave7PhaseThreeCurrentMinCritical OBJECT-TYPE
    SYNTAX      DisplayString
    MAX-ACCESS  read-write
    STATUS      current
    DESCRIPTION
	"The power of phase one"
    ::= { slave7PhaseThree 7}
	
slave7PhaseThreeCurrentMaxCritical OBJECT-TYPE
    SYNTAX      DisplayString
    MAX-ACCESS  read-write
    STATUS      current
    DESCRIPTION
	"The power of phase one"
    ::= { slave7PhaseThree 8}
	
slave7PhaseThreeCurrentMax OBJECT-TYPE
    SYNTAX      DisplayString
    MAX-ACCESS  read-write
    STATUS      current
    DESCRIPTION
	"The power of phase one"
    ::= { slave7PhaseThree 9}
	
slave7PhaseThreeVoltageMin OBJECT-TYPE
    SYNTAX      DisplayString
    MAX-ACCESS  read-write
    STATUS      current
    DESCRIPTION
	"The power of phase one"
    ::= { slave7PhaseThree 10}
	
slave7PhaseThreeVoltageMinCritical OBJECT-TYPE
    SYNTAX      DisplayString
    MAX-ACCESS  read-write
    STATUS      current
    DESCRIPTION
	"The power of phase one"
    ::= { slave7PhaseThree 11}

slave7PhaseThreeVoltageMaxCritical OBJECT-TYPE
    SYNTAX      DisplayString
    MAX-ACCESS  read-write
    STATUS      current
    DESCRIPTION
	"The power of phase one"
    ::= { slave7PhaseThree 12}
	
slave7PhaseThreeVoltageMax OBJECT-TYPE
    SYNTAX      DisplayString
    MAX-ACCESS  read-write
    STATUS      current
    DESCRIPTION
	"The power of phase one"
    ::= { slave7PhaseThree 13}
	
	
-------------------------------slave7 circuit--------------------	
slave7Circuit OBJECT IDENTIFIER ::= { slave7 3}	

slave7CircuitOne OBJECT IDENTIFIER ::= { slave7Circuit 1}	    
slave7CircuitOneBreaker OBJECT-TYPE
    SYNTAX      DisplayString
    MAX-ACCESS  read-only
    STATUS      current
    DESCRIPTION
	"The power of phase one"
    ::= { slave7CircuitOne 1}
	
slave7CircuitOneManagementBit OBJECT-TYPE
    SYNTAX      DisplayString
    MAX-ACCESS  read-only
    STATUS      current
    DESCRIPTION
	"The power of phase one"
    ::= { slave7CircuitOne 2}	

slave7CircuitOneCurrent OBJECT-TYPE
    SYNTAX      DisplayString
    MAX-ACCESS  read-only
    STATUS      current
    DESCRIPTION
	"The power of phase one"
    ::= { slave7CircuitOne 3}

slave7CircuitOneVoltage OBJECT-TYPE
    SYNTAX      DisplayString
    MAX-ACCESS  read-only
    STATUS      current
    DESCRIPTION
	"The power of phase one"
    ::= { slave7CircuitOne 4}

slave7CircuitOneEnergy OBJECT-TYPE
    SYNTAX      DisplayString
    MAX-ACCESS  read-only
    STATUS      current
    DESCRIPTION
	"The power of phase one"
    ::= { slave7CircuitOne 5}	
	
slave7CircuitOnePower OBJECT-TYPE
    SYNTAX      DisplayString
    MAX-ACCESS  read-only
    STATUS      current
    DESCRIPTION
	"The power of phase one"
    ::= { slave7CircuitOne 6}
	
slave7CircuitOneCurrentMin OBJECT-TYPE
    SYNTAX      DisplayString
    MAX-ACCESS  read-write
    STATUS      current
    DESCRIPTION
	"The power of phase one"
    ::= { slave7CircuitOne 7}	
	
slave7CircuitOneCurrentMinCritical OBJECT-TYPE
    SYNTAX      DisplayString
    MAX-ACCESS  read-write
    STATUS      current
    DESCRIPTION
	"The power of phase one"
    ::= { slave7CircuitOne 8}
	
slave7CircuitOneCurrentMaxCritical OBJECT-TYPE
    SYNTAX      DisplayString
    MAX-ACCESS  read-write
    STATUS      current
    DESCRIPTION
	"The power of phase one"
    ::= { slave7CircuitOne 9}
	
slave7CircuitOneCurrentMax OBJECT-TYPE
    SYNTAX      DisplayString
    MAX-ACCESS  read-write
    STATUS      current
    DESCRIPTION
	"The power of phase one"
    ::= { slave7CircuitOne 10}
	

slave7CircuitTwo OBJECT IDENTIFIER ::= { slave7Circuit 2}	    
slave7CircuitTwoBreaker OBJECT-TYPE
    SYNTAX      DisplayString
    MAX-ACCESS  read-only
    STATUS      current
    DESCRIPTION
	"The power of phase one"
    ::= { slave7CircuitTwo 1}
	
slave7CircuitTwoManagementBit OBJECT-TYPE
    SYNTAX      DisplayString
    MAX-ACCESS  read-only
    STATUS      current
    DESCRIPTION
	"The power of phase one"
    ::= { slave7CircuitTwo 2}	

slave7CircuitTwoCurrent OBJECT-TYPE
    SYNTAX      DisplayString
    MAX-ACCESS  read-only
    STATUS      current
    DESCRIPTION
	"The power of phase one"
    ::= { slave7CircuitTwo 3}

slave7CircuitTwoVoltage OBJECT-TYPE
    SYNTAX      DisplayString
    MAX-ACCESS  read-only
    STATUS      current
    DESCRIPTION
	"The power of phase one"
    ::= { slave7CircuitTwo 4}

slave7CircuitTwoEnergy OBJECT-TYPE
    SYNTAX      DisplayString
    MAX-ACCESS  read-only
    STATUS      current
    DESCRIPTION
	"The power of phase one"
    ::= { slave7CircuitTwo 5}	
	
slave7CircuitTwoPower OBJECT-TYPE
    SYNTAX      DisplayString
    MAX-ACCESS  read-only
    STATUS      current
    DESCRIPTION
	"The power of phase one"
    ::= { slave7CircuitTwo 6}
	
slave7CircuitTwoCurrentMin OBJECT-TYPE
    SYNTAX      DisplayString
    MAX-ACCESS  read-write
    STATUS      current
    DESCRIPTION
	"The power of phase one"
    ::= { slave7CircuitTwo 7}	
	
slave7CircuitTwoCurrentMinCritical OBJECT-TYPE
    SYNTAX      DisplayString
    MAX-ACCESS  read-write
    STATUS      current
    DESCRIPTION
	"The power of phase one"
    ::= { slave7CircuitTwo 8}
	
slave7CircuitTwoCurrentMaxCritical OBJECT-TYPE
    SYNTAX      DisplayString
    MAX-ACCESS  read-write
    STATUS      current
    DESCRIPTION
	"The power of phase one"
    ::= { slave7CircuitTwo 9}
	
slave7CircuitTwoCurrentMax OBJECT-TYPE
    SYNTAX      DisplayString
    MAX-ACCESS  read-write
    STATUS      current
    DESCRIPTION
	"The power of phase one"
    ::= { slave7CircuitTwo 10}
	
	
slave7CircuitThree OBJECT IDENTIFIER ::= { slave7Circuit 3}	    
slave7CircuitThreeBreaker OBJECT-TYPE
    SYNTAX      DisplayString
    MAX-ACCESS  read-only
    STATUS      current
    DESCRIPTION
	"The power of phase one"
    ::= { slave7CircuitThree 1}
	
slave7CircuitThreeManagementBit OBJECT-TYPE
    SYNTAX      DisplayString
    MAX-ACCESS  read-only
    STATUS      current
    DESCRIPTION
	"The power of phase one"
    ::= { slave7CircuitThree 2}	

slave7CircuitThreeCurrent OBJECT-TYPE
    SYNTAX      DisplayString
    MAX-ACCESS  read-only
    STATUS      current
    DESCRIPTION
	"The power of phase one"
    ::= { slave7CircuitThree 3}

slave7CircuitThreeVoltage OBJECT-TYPE
    SYNTAX      DisplayString
    MAX-ACCESS  read-only
    STATUS      current
    DESCRIPTION
	"The power of phase one"
    ::= { slave7CircuitThree 4}

slave7CircuitThreeEnergy OBJECT-TYPE
    SYNTAX      DisplayString
    MAX-ACCESS  read-only
    STATUS      current
    DESCRIPTION
	"The power of phase one"
    ::= { slave7CircuitThree 5}	
	
slave7CircuitThreePower OBJECT-TYPE
    SYNTAX      DisplayString
    MAX-ACCESS  read-only
    STATUS      current
    DESCRIPTION
	"The power of phase one"
    ::= { slave7CircuitThree 6}
	
slave7CircuitThreeCurrentMin OBJECT-TYPE
    SYNTAX      DisplayString
    MAX-ACCESS  read-write
    STATUS      current
    DESCRIPTION
	"The power of phase one"
    ::= { slave7CircuitThree 7}	
	
slave7CircuitThreeCurrentMinCritical OBJECT-TYPE
    SYNTAX      DisplayString
    MAX-ACCESS  read-write
    STATUS      current
    DESCRIPTION
	"The power of phase one"
    ::= { slave7CircuitThree 8}
	
slave7CircuitThreeCurrentMaxCritical OBJECT-TYPE
    SYNTAX      DisplayString
    MAX-ACCESS  read-write
    STATUS      current
    DESCRIPTION
	"The power of phase one"
    ::= { slave7CircuitThree 9}
	
slave7CircuitThreeCurrentMax OBJECT-TYPE
    SYNTAX      DisplayString
    MAX-ACCESS  read-write
    STATUS      current
    DESCRIPTION
	"The power of phase one"
    ::= { slave7CircuitThree 10}
	
	
slave7CircuitFour OBJECT IDENTIFIER ::= { slave7Circuit 4}	    
slave7CircuitFourBreaker OBJECT-TYPE
    SYNTAX      DisplayString
    MAX-ACCESS  read-only
    STATUS      current
    DESCRIPTION
	"The power of phase one"
    ::= { slave7CircuitFour 1}
	
slave7CircuitFourManagementBit OBJECT-TYPE
    SYNTAX      DisplayString
    MAX-ACCESS  read-only
    STATUS      current
    DESCRIPTION
	"The power of phase one"
    ::= { slave7CircuitFour 2}	

slave7CircuitFourCurrent OBJECT-TYPE
    SYNTAX      DisplayString
    MAX-ACCESS  read-only
    STATUS      current
    DESCRIPTION
	"The power of phase one"
    ::= { slave7CircuitFour 3}

slave7CircuitFourVoltage OBJECT-TYPE
    SYNTAX      DisplayString
    MAX-ACCESS  read-only
    STATUS      current
    DESCRIPTION
	"The power of phase one"
    ::= { slave7CircuitFour 4}

slave7CircuitFourEnergy OBJECT-TYPE
    SYNTAX      DisplayString
    MAX-ACCESS  read-only
    STATUS      current
    DESCRIPTION
	"The power of phase one"
    ::= { slave7CircuitFour 5}	
	
slave7CircuitFourPower OBJECT-TYPE
    SYNTAX      DisplayString
    MAX-ACCESS  read-only
    STATUS      current
    DESCRIPTION
	"The power of phase one"
    ::= { slave7CircuitFour 6}
	
slave7CircuitFourCurrentMin OBJECT-TYPE
    SYNTAX      DisplayString
    MAX-ACCESS  read-write
    STATUS      current
    DESCRIPTION
	"The power of phase one"
    ::= { slave7CircuitFour 7}	
	
slave7CircuitFourCurrentMinCritical OBJECT-TYPE
    SYNTAX      DisplayString
    MAX-ACCESS  read-write
    STATUS      current
    DESCRIPTION
	"The power of phase one"
    ::= { slave7CircuitFour 8}
	
slave7CircuitFourCurrentMaxCritical OBJECT-TYPE
    SYNTAX      DisplayString
    MAX-ACCESS  read-write
    STATUS      current
    DESCRIPTION
	"The power of phase one"
    ::= { slave7CircuitFour 9}
	
slave7CircuitFourCurrentMax OBJECT-TYPE
    SYNTAX      DisplayString
    MAX-ACCESS  read-write
    STATUS      current
    DESCRIPTION
	"The power of phase one"
    ::= { slave7CircuitFour 10}
	
	
slave7CircuitFive OBJECT IDENTIFIER ::= { slave7Circuit 5}	    
slave7CircuitFiveBreaker OBJECT-TYPE
    SYNTAX      DisplayString
    MAX-ACCESS  read-only
    STATUS      current
    DESCRIPTION
	"The power of phase one"
    ::= { slave7CircuitFive 1}
	
slave7CircuitFiveManagementBit OBJECT-TYPE
    SYNTAX      DisplayString
    MAX-ACCESS  read-only
    STATUS      current
    DESCRIPTION
	"The power of phase one"
    ::= { slave7CircuitFive 2}	

slave7CircuitFiveCurrent OBJECT-TYPE
    SYNTAX      DisplayString
    MAX-ACCESS  read-only
    STATUS      current
    DESCRIPTION
	"The power of phase one"
    ::= { slave7CircuitFive 3}

slave7CircuitFiveVoltage OBJECT-TYPE
    SYNTAX      DisplayString
    MAX-ACCESS  read-only
    STATUS      current
    DESCRIPTION
	"The power of phase one"
    ::= { slave7CircuitFive 4}

slave7CircuitFiveEnergy OBJECT-TYPE
    SYNTAX      DisplayString
    MAX-ACCESS  read-only
    STATUS      current
    DESCRIPTION
	"The power of phase one"
    ::= { slave7CircuitFive 5}	
	
slave7CircuitFivePower OBJECT-TYPE
    SYNTAX      DisplayString
    MAX-ACCESS  read-only
    STATUS      current
    DESCRIPTION
	"The power of phase one"
    ::= { slave7CircuitFive 6}
		
slave7CircuitFiveCurrentMin OBJECT-TYPE
    SYNTAX      DisplayString
    MAX-ACCESS  read-write
    STATUS      current
    DESCRIPTION
	"The power of phase one"
    ::= { slave7CircuitFive 7}	
	
slave7CircuitFiveCurrentMinCritical OBJECT-TYPE
    SYNTAX      DisplayString
    MAX-ACCESS  read-write
    STATUS      current
    DESCRIPTION
	"The power of phase one"
    ::= { slave7CircuitFive 8}
	
slave7CircuitFiveCurrentMaxCritical OBJECT-TYPE
    SYNTAX      DisplayString
    MAX-ACCESS  read-write
    STATUS      current
    DESCRIPTION
	"The power of phase one"
    ::= { slave7CircuitFive 9}
	
slave7CircuitFiveCurrentMax OBJECT-TYPE
    SYNTAX      DisplayString
    MAX-ACCESS  read-write
    STATUS      current
    DESCRIPTION
	"The power of phase one"
    ::= { slave7CircuitFive 10}

	
slave7CircuitSix OBJECT IDENTIFIER ::= { slave7Circuit 6}	    
slave7CircuitSixBreaker OBJECT-TYPE
    SYNTAX      DisplayString
    MAX-ACCESS  read-only
    STATUS      current
    DESCRIPTION
	"The power of phase one"
    ::= { slave7CircuitSix 1}
	
slave7CircuitSixManagementBit OBJECT-TYPE
    SYNTAX      DisplayString
    MAX-ACCESS  read-only
    STATUS      current
    DESCRIPTION
	"The power of phase one"
    ::= { slave7CircuitSix 2}	

slave7CircuitSixCurrent OBJECT-TYPE
    SYNTAX      DisplayString
    MAX-ACCESS  read-only
    STATUS      current
    DESCRIPTION
	"The power of phase one"
    ::= { slave7CircuitSix 3}

slave7CircuitSixVoltage OBJECT-TYPE
    SYNTAX      DisplayString
    MAX-ACCESS  read-only
    STATUS      current
    DESCRIPTION
	"The power of phase one"
    ::= { slave7CircuitSix 4}

slave7CircuitSixEnergy OBJECT-TYPE
    SYNTAX      DisplayString
    MAX-ACCESS  read-only
    STATUS      current
    DESCRIPTION
	"The power of phase one"
    ::= { slave7CircuitSix 5}	
	
slave7CircuitSixPower OBJECT-TYPE
    SYNTAX      DisplayString
    MAX-ACCESS  read-only
    STATUS      current
    DESCRIPTION
	"The power of phase one"
    ::= { slave7CircuitSix 6}
	
slave7CircuitSixCurrentMin OBJECT-TYPE
    SYNTAX      DisplayString
    MAX-ACCESS  read-write
    STATUS      current
    DESCRIPTION
	"The power of phase one"
    ::= { slave7CircuitSix 7}	
	
slave7CircuitSixCurrentMinCritical OBJECT-TYPE
    SYNTAX      DisplayString
    MAX-ACCESS  read-write
    STATUS      current
    DESCRIPTION
	"The power of phase one"
    ::= { slave7CircuitSix 8}
	
slave7CircuitSixCurrentMaxCritical OBJECT-TYPE
    SYNTAX      DisplayString
    MAX-ACCESS  read-write
    STATUS      current
    DESCRIPTION
	"The power of phase one"
    ::= { slave7CircuitSix 9}
	
slave7CircuitSixCurrentMax OBJECT-TYPE
    SYNTAX      DisplayString
    MAX-ACCESS  read-write
    STATUS      current
    DESCRIPTION
	"The power of phase one"
    ::= { slave7CircuitSix 10}

	
-------------------------------slave7 sensor------------------------	
slave7Sensor OBJECT IDENTIFIER ::= { slave7 4}
slave7SensorTemperatureOne OBJECT-TYPE
    SYNTAX      DisplayString
    MAX-ACCESS  read-only
    STATUS      current
    DESCRIPTION
	"This is the first device."
    ::= { slave7Sensor 1}
	
slave7SensorTemperatureTwo OBJECT-TYPE
    SYNTAX      DisplayString
    MAX-ACCESS  read-only
    STATUS      current
    DESCRIPTION
	"This is the first device."
    ::= { slave7Sensor 2}

slave7SensorHumidityOne OBJECT-TYPE
    SYNTAX      DisplayString
    MAX-ACCESS  read-only
    STATUS      current
    DESCRIPTION
	"This is the first device."
    ::= { slave7Sensor 3}

slave7SensorHumidityTwo OBJECT-TYPE
    SYNTAX      DisplayString
    MAX-ACCESS  read-only
    STATUS      current
    DESCRIPTION
	"This is the first device."
    ::= { slave7Sensor 4}	

slave7SensorDoorOne OBJECT-TYPE
    SYNTAX      DisplayString
    MAX-ACCESS  read-only
    STATUS      current
    DESCRIPTION
	"This is the first device."
    ::= { slave7Sensor 5}

slave7SensorDoorTwo OBJECT-TYPE
    SYNTAX      DisplayString
    MAX-ACCESS  read-only
    STATUS      current
    DESCRIPTION
	"This is the first device."
    ::= { slave7Sensor 6}	
	
slave7SensorSmoke OBJECT-TYPE
    SYNTAX      DisplayString
    MAX-ACCESS  read-only
    STATUS      current
    DESCRIPTION
	"This is the first device."
    ::= { slave7Sensor 7}
	
slave7SensorWater OBJECT-TYPE
    SYNTAX      DisplayString
    MAX-ACCESS  read-only
    STATUS      current
    DESCRIPTION
	"This is the first device."
    ::= { slave7Sensor 8}
	
slave7SensorTemperatureOneMin OBJECT-TYPE
    SYNTAX      DisplayString
    MAX-ACCESS  read-write
    STATUS      current
    DESCRIPTION
	"This is the first device."
    ::= { slave7Sensor 9}
	
slave7SensorTemperatureOneMinCritical OBJECT-TYPE
    SYNTAX      DisplayString
    MAX-ACCESS  read-write
    STATUS      current
    DESCRIPTION
	"This is the first device."
    ::= { slave7Sensor 10}	
	
slave7SensorTemperatureOneMaxCritical OBJECT-TYPE
    SYNTAX      DisplayString
    MAX-ACCESS  read-write
    STATUS      current
    DESCRIPTION
	"This is the first device."
    ::= { slave7Sensor 11}
	
slave7SensorTemperatureOneMax OBJECT-TYPE
    SYNTAX      DisplayString
    MAX-ACCESS  read-write
    STATUS      current
    DESCRIPTION
	"This is the first device."
    ::= { slave7Sensor 12}

slave7SensorTemperatureTwoMin OBJECT-TYPE
    SYNTAX      DisplayString
    MAX-ACCESS  read-write
    STATUS      current
    DESCRIPTION
	"This is the first device."
    ::= { slave7Sensor 13}
	
slave7SensorTemperatureTwoMinCritical OBJECT-TYPE
    SYNTAX      DisplayString
    MAX-ACCESS  read-write
    STATUS      current
    DESCRIPTION
	"This is the first device."
    ::= { slave7Sensor 14}	
	
slave7SensorTemperatureTwoMaxCritical OBJECT-TYPE
    SYNTAX      DisplayString
    MAX-ACCESS  read-write
    STATUS      current
    DESCRIPTION
	"This is the first device."
    ::= { slave7Sensor 15}
	
slave7SensorTemperatureTwoMax OBJECT-TYPE
    SYNTAX      DisplayString
    MAX-ACCESS  read-write
    STATUS      current
    DESCRIPTION
	"This is the first device."
    ::= { slave7Sensor 16}
	
slave7SensorHumidityOneMin OBJECT-TYPE
    SYNTAX      DisplayString
    MAX-ACCESS  read-write
    STATUS      current
    DESCRIPTION
	"This is the first device."
    ::= { slave7Sensor 17}
	
slave7SensorHumidityOneMinCritical OBJECT-TYPE
    SYNTAX      DisplayString
    MAX-ACCESS  read-write
    STATUS      current
    DESCRIPTION
	"This is the first device."
    ::= { slave7Sensor 18}	
	
slave7SensorHumidityOneMaxCritical OBJECT-TYPE
    SYNTAX      DisplayString
    MAX-ACCESS  read-write
    STATUS      current
    DESCRIPTION
	"This is the first device."
    ::= { slave7Sensor 19}
	
slave7SensorHumidityOneMax OBJECT-TYPE
    SYNTAX      DisplayString
    MAX-ACCESS  read-write
    STATUS      current
    DESCRIPTION
	"This is the first device."
    ::= { slave7Sensor 20}

slave7SensorHumidityTwoMin OBJECT-TYPE
    SYNTAX      DisplayString
    MAX-ACCESS  read-write
    STATUS      current
    DESCRIPTION
	"This is the first device."
    ::= { slave7Sensor 21}
	
slave7SensorHumidityTwoMinCritical OBJECT-TYPE
    SYNTAX      DisplayString
    MAX-ACCESS  read-write
    STATUS      current
    DESCRIPTION
	"This is the first device."
    ::= { slave7Sensor 22}	
	
slave7SensorHumidityTwoMaxCritical OBJECT-TYPE
    SYNTAX      DisplayString
    MAX-ACCESS  read-write
    STATUS      current
    DESCRIPTION
	"This is the first device."
    ::= { slave7Sensor 23}
	
slave7SensorHumidityTwoMax OBJECT-TYPE
    SYNTAX      DisplayString
    MAX-ACCESS  read-write
    STATUS      current
    DESCRIPTION
	"This is the first device."
    ::= { slave7Sensor 24}
	
-------------------------------slave7 output name------------------------	
slave7OutputName OBJECT IDENTIFIER ::= { slave7 5}
slave7OutputNameOne OBJECT-TYPE
    SYNTAX      DisplayString
    MAX-ACCESS  read-write
    STATUS      current
    DESCRIPTION
	"The first output name of slave7"
    ::= { slave7OutputName 1}

slave7OutputNameTwo OBJECT-TYPE
    SYNTAX      DisplayString
    MAX-ACCESS  read-write
    STATUS      current
    DESCRIPTION
	"The second output name of slave7"
    ::= { slave7OutputName 2}

slave7OutputNameThree OBJECT-TYPE
    SYNTAX      DisplayString
    MAX-ACCESS  read-write
    STATUS      current
    DESCRIPTION
	"The second output name of slave7"
    ::= { slave7OutputName 3}

slave7OutputNameFour OBJECT-TYPE
    SYNTAX      DisplayString
    MAX-ACCESS  read-write
    STATUS      current
    DESCRIPTION
	"The second output name of slave7"
    ::= { slave7OutputName 4}

slave7OutputNameFive OBJECT-TYPE
    SYNTAX      DisplayString
    MAX-ACCESS  read-write
    STATUS      current
    DESCRIPTION
	"The second output name of slave7"
    ::= { slave7OutputName 5}

slave7OutputNameSix OBJECT-TYPE
    SYNTAX      DisplayString
    MAX-ACCESS  read-write
    STATUS      current
    DESCRIPTION
	"The second output name of slave7"
    ::= { slave7OutputName 6}

slave7OutputNameSeven OBJECT-TYPE
    SYNTAX      DisplayString
    MAX-ACCESS  read-write
    STATUS      current
    DESCRIPTION
	"The second output name of slave7"
    ::= { slave7OutputName 7}

slave7OutputNameEight OBJECT-TYPE
    SYNTAX      DisplayString
    MAX-ACCESS  read-write
    STATUS      current
    DESCRIPTION
	"The second output name of slave7"
    ::= { slave7OutputName 8}

slave7OutputNameNine OBJECT-TYPE
    SYNTAX      DisplayString
    MAX-ACCESS  read-write
    STATUS      current
    DESCRIPTION
	"The second output name of slave7"
    ::= { slave7OutputName 9}

slave7OutputNameTen OBJECT-TYPE
    SYNTAX      DisplayString
    MAX-ACCESS  read-write
    STATUS      current
    DESCRIPTION
	"The second output name of slave7"
    ::= { slave7OutputName 10}

slave7OutputNameEleven OBJECT-TYPE
    SYNTAX      DisplayString
    MAX-ACCESS  read-write
    STATUS      current
    DESCRIPTION
	"The second output name of slave7"
    ::= { slave7OutputName 11}

slave7OutputNameTwel OBJECT-TYPE
    SYNTAX      DisplayString
    MAX-ACCESS  read-write
    STATUS      current
    DESCRIPTION
	"The second output name of slave7"
    ::= { slave7OutputName 12}

slave7OutputNameThirteen OBJECT-TYPE
    SYNTAX      DisplayString
    MAX-ACCESS  read-write
    STATUS      current
    DESCRIPTION
	"The second output name of slave7"
    ::= { slave7OutputName 13}

slave7OutputNameFourteen OBJECT-TYPE
    SYNTAX      DisplayString
    MAX-ACCESS  read-write
    STATUS      current
    DESCRIPTION
	"The second output name of slave7"
    ::= { slave7OutputName 14}

slave7OutputNameFifteen OBJECT-TYPE
    SYNTAX      DisplayString
    MAX-ACCESS  read-write
    STATUS      current
    DESCRIPTION
	"The second output name of slave7"
    ::= { slave7OutputName 15}

slave7OutputNameSixteen OBJECT-TYPE
    SYNTAX      DisplayString
    MAX-ACCESS  read-write
    STATUS      current
    DESCRIPTION
	"The second output name of slave7"
    ::= { slave7OutputName 16}

slave7OutputNameSeventeen OBJECT-TYPE
    SYNTAX      DisplayString
    MAX-ACCESS  read-write
    STATUS      current
    DESCRIPTION
	"The second output name of slave7"
    ::= { slave7OutputName 17}

slave7OutputNameEighteen OBJECT-TYPE
    SYNTAX      DisplayString
    MAX-ACCESS  read-write
    STATUS      current
    DESCRIPTION
	"The second output name of slave7"
    ::= { slave7OutputName 18}
	
slave7OutputNameNineteen OBJECT-TYPE
    SYNTAX      DisplayString
    MAX-ACCESS  read-write
    STATUS      current
    DESCRIPTION
	"The second output name of slave7"
    ::= { slave7OutputName 19}
	
slave7OutputNametwenty OBJECT-TYPE
    SYNTAX      DisplayString
    MAX-ACCESS  read-write
    STATUS      current
    DESCRIPTION
	"The second output name of slave7"
    ::= { slave7OutputName 20}
	
slave7OutputNameTwentyone OBJECT-TYPE
    SYNTAX      DisplayString
    MAX-ACCESS  read-write
    STATUS      current
    DESCRIPTION
	"The second output name of slave7"
    ::= { slave7OutputName 21}
	
slave7OutputNameTwentyonetwo OBJECT-TYPE
    SYNTAX      DisplayString
    MAX-ACCESS  read-write
    STATUS      current
    DESCRIPTION
	"The second output name of slave7"
    ::= { slave7OutputName 22}
	
slave7OutputNameTwentythree OBJECT-TYPE
    SYNTAX      DisplayString
    MAX-ACCESS  read-write
    STATUS      current
    DESCRIPTION
	"The second output name of slave7"
    ::= { slave7OutputName 23}
	
slave7OutputNameTwentyfour OBJECT-TYPE
    SYNTAX      DisplayString
    MAX-ACCESS  read-write
    STATUS      current
    DESCRIPTION
	"The second output name of slave7"
    ::= { slave7OutputName 24}
	
slave7OutputNameTwentyfive OBJECT-TYPE
    SYNTAX      DisplayString
    MAX-ACCESS  read-write
    STATUS      current
    DESCRIPTION
	"The second output name of slave7"
    ::= { slave7OutputName 25}
	
slave7OutputNameTwentysix OBJECT-TYPE
    SYNTAX      DisplayString
    MAX-ACCESS  read-write
    STATUS      current
    DESCRIPTION
	"The second output name of slave7"
    ::= { slave7OutputName 26}
	
slave7OutputNameTwentyseven OBJECT-TYPE
    SYNTAX      DisplayString
    MAX-ACCESS  read-write
    STATUS      current
    DESCRIPTION
	"The second output name of slave7"
    ::= { slave7OutputName 27}
	
slave7OutputNameTwentyeight OBJECT-TYPE
    SYNTAX      DisplayString
    MAX-ACCESS  read-write
    STATUS      current
    DESCRIPTION
	"The second output name of slave7"
    ::= { slave7OutputName 28}	
slave7OutputNameTwentynine OBJECT-TYPE
    SYNTAX      DisplayString
    MAX-ACCESS  read-write
    STATUS      current
    DESCRIPTION
	"The second output name of slave7"
    ::= { slave7OutputName 29}
	
slave7OutputNameThirty OBJECT-TYPE
    SYNTAX      DisplayString
    MAX-ACCESS  read-write
    STATUS      current
    DESCRIPTION
	"The second output name of slave7"
    ::= { slave7OutputName 30}
	
slave7OutputNameThirtyone OBJECT-TYPE
    SYNTAX      DisplayString
    MAX-ACCESS  read-write
    STATUS      current
    DESCRIPTION
	"The second output name of slave7"
    ::= { slave7OutputName 31}
	
slave7OutputNameThirtytwo OBJECT-TYPE
    SYNTAX      DisplayString
    MAX-ACCESS  read-write
    STATUS      current
    DESCRIPTION
	"The second output name of slave7"
    ::= { slave7OutputName 32}
	
slave7OutputNameThirtythree OBJECT-TYPE
    SYNTAX      DisplayString
    MAX-ACCESS  read-write
    STATUS      current
    DESCRIPTION
	"The second output name of slave7"
    ::= { slave7OutputName 33}
	
slave7OutputNameThirtyfour OBJECT-TYPE
    SYNTAX      DisplayString
    MAX-ACCESS  read-write
    STATUS      current
    DESCRIPTION
	"The second output name of slave7"
    ::= { slave7OutputName 34}
	
slave7OutputNameThirtyfive OBJECT-TYPE
    SYNTAX      DisplayString
    MAX-ACCESS  read-write
    STATUS      current
    DESCRIPTION
	"The second output name of slave7"
    ::= { slave7OutputName 35}
	
slave7OutputNameThirtysix OBJECT-TYPE
    SYNTAX      DisplayString
    MAX-ACCESS  read-write
    STATUS      current
    DESCRIPTION
	"The second output name of slave7"
    ::= { slave7OutputName 36}
	
slave7OutputNameThirtyseven OBJECT-TYPE
    SYNTAX      DisplayString
    MAX-ACCESS  read-write
    STATUS      current
    DESCRIPTION
	"The second output name of slave7"
    ::= { slave7OutputName 37}
	
slave7OutputNameThirtyeight OBJECT-TYPE
    SYNTAX      DisplayString
    MAX-ACCESS  read-write
    STATUS      current
    DESCRIPTION
	"The second output name of slave7"
    ::= { slave7OutputName 38}
	
slave7OutputNameThirtynine OBJECT-TYPE
    SYNTAX      DisplayString
    MAX-ACCESS  read-write
    STATUS      current
    DESCRIPTION
	"The second output name of slave7"
    ::= { slave7OutputName 39}
	
slave7OutputNameFourty OBJECT-TYPE
    SYNTAX      DisplayString
    MAX-ACCESS  read-write
    STATUS      current
    DESCRIPTION
	"The second output name of slave7"
    ::= { slave7OutputName 40}
	
slave7OutputNameFourtyone OBJECT-TYPE
    SYNTAX      DisplayString
    MAX-ACCESS  read-write
    STATUS      current
    DESCRIPTION
	"The second output name of slave7"
    ::= { slave7OutputName 41}
	
slave7OutputNameFourtytwo OBJECT-TYPE
    SYNTAX      DisplayString
    MAX-ACCESS  read-write
    STATUS      current
    DESCRIPTION
	"The second output name of slave7"
    ::= { slave7OutputName 42}	

	
-------------------------------slave7 output delay------------------------	
slave7OutputDelay OBJECT IDENTIFIER ::= { slave7 6}	
slave7OutputDelayOne OBJECT-TYPE
    SYNTAX      DisplayString
    MAX-ACCESS  read-write
    STATUS      current
    DESCRIPTION
	"The first output name of slave7"
    ::= { slave7OutputDelay 1}

slave7OutputDelayTwo OBJECT-TYPE
    SYNTAX      DisplayString
    MAX-ACCESS  read-write
    STATUS      current
    DESCRIPTION
	"The second output name of slave7"
    ::= { slave7OutputDelay 2}

slave7OutputDelayThree OBJECT-TYPE
    SYNTAX      DisplayString
    MAX-ACCESS  read-write
    STATUS      current
    DESCRIPTION
	"The second output name of slave7"
    ::= { slave7OutputDelay 3}

slave7OutputDelayFour OBJECT-TYPE
    SYNTAX      DisplayString
    MAX-ACCESS  read-write
    STATUS      current
    DESCRIPTION
	"The second output name of slave7"
    ::= { slave7OutputDelay 4}

slave7OutputDelayFive OBJECT-TYPE
    SYNTAX      DisplayString
    MAX-ACCESS  read-write
    STATUS      current
    DESCRIPTION
	"The second output name of slave7"
    ::= { slave7OutputDelay 5}

slave7OutputDelaySix OBJECT-TYPE
    SYNTAX      DisplayString
    MAX-ACCESS  read-write
    STATUS      current
    DESCRIPTION
	"The second output name of slave7"
    ::= { slave7OutputDelay 6}

slave7OutputDelaySeven OBJECT-TYPE
    SYNTAX      DisplayString
    MAX-ACCESS  read-write
    STATUS      current
    DESCRIPTION
	"The second output name of slave7"
    ::= { slave7OutputDelay 7}

slave7OutputDelayEight OBJECT-TYPE
    SYNTAX      DisplayString
    MAX-ACCESS  read-write
    STATUS      current
    DESCRIPTION
	"The second output name of slave7"
    ::= { slave7OutputDelay 8}

slave7OutputDelayNine OBJECT-TYPE
    SYNTAX      DisplayString
    MAX-ACCESS  read-write
    STATUS      current
    DESCRIPTION
	"The second output name of slave7"
    ::= { slave7OutputDelay 9}

slave7OutputDelayTen OBJECT-TYPE
    SYNTAX      DisplayString
    MAX-ACCESS  read-write
    STATUS      current
    DESCRIPTION
	"The second output name of slave7"
    ::= { slave7OutputDelay 10}

slave7OutputDelayEleven OBJECT-TYPE
    SYNTAX      DisplayString
    MAX-ACCESS  read-write
    STATUS      current
    DESCRIPTION
	"The second output name of slave7"
    ::= { slave7OutputDelay 11}

slave7OutputDelayTwel OBJECT-TYPE
    SYNTAX      DisplayString
    MAX-ACCESS  read-write
    STATUS      current
    DESCRIPTION
	"The second output name of slave7"
    ::= { slave7OutputDelay 12}

slave7OutputDelayThirteen OBJECT-TYPE
    SYNTAX      DisplayString
    MAX-ACCESS  read-write
    STATUS      current
    DESCRIPTION
	"The second output name of slave7"
    ::= { slave7OutputDelay 13}

slave7OutputDelayFourteen OBJECT-TYPE
    SYNTAX      DisplayString
    MAX-ACCESS  read-write
    STATUS      current
    DESCRIPTION
	"The second output name of slave7"
    ::= { slave7OutputDelay 14}

slave7OutputDelayFifteen OBJECT-TYPE
    SYNTAX      DisplayString
    MAX-ACCESS  read-write
    STATUS      current
    DESCRIPTION
	"The second output name of slave7"
    ::= { slave7OutputDelay 15}

slave7OutputDelaySixteen OBJECT-TYPE
    SYNTAX      DisplayString
    MAX-ACCESS  read-write
    STATUS      current
    DESCRIPTION
	"The second output name of slave7"
    ::= { slave7OutputDelay 16}

slave7OutputDelaySeventeen OBJECT-TYPE
    SYNTAX      DisplayString
    MAX-ACCESS  read-write
    STATUS      current
    DESCRIPTION
	"The second output name of slave7"
    ::= { slave7OutputDelay 17}

slave7OutputDelayEighteen OBJECT-TYPE
    SYNTAX      DisplayString
    MAX-ACCESS  read-write
    STATUS      current
    DESCRIPTION
	"The second output name of slave7"
    ::= { slave7OutputDelay 18}
	
slave7OutputDelayNineteen OBJECT-TYPE
    SYNTAX      DisplayString
    MAX-ACCESS  read-write
    STATUS      current
    DESCRIPTION
	"The second output name of slave7"
    ::= { slave7OutputDelay 19}
	
slave7OutputDelaytwenty OBJECT-TYPE
    SYNTAX      DisplayString
    MAX-ACCESS  read-write
    STATUS      current
    DESCRIPTION
	"The second output name of slave7"
    ::= { slave7OutputDelay 20}
	
slave7OutputDelayTwentyone OBJECT-TYPE
    SYNTAX      DisplayString
    MAX-ACCESS  read-write
    STATUS      current
    DESCRIPTION
	"The second output name of slave7"
    ::= { slave7OutputDelay 21}
	
slave7OutputDelayTwentyonetwo OBJECT-TYPE
    SYNTAX      DisplayString
    MAX-ACCESS  read-write
    STATUS      current
    DESCRIPTION
	"The second output name of slave7"
    ::= { slave7OutputDelay 22}
	
slave7OutputDelayTwentythree OBJECT-TYPE
    SYNTAX      DisplayString
    MAX-ACCESS  read-write
    STATUS      current
    DESCRIPTION
	"The second output name of slave7"
    ::= { slave7OutputDelay 23}
	
slave7OutputDelayTwentyfour OBJECT-TYPE
    SYNTAX      DisplayString
    MAX-ACCESS  read-write
    STATUS      current
    DESCRIPTION
	"The second output name of slave7"
    ::= { slave7OutputDelay 24}
	
slave7OutputDelayTwentyfive OBJECT-TYPE
    SYNTAX      DisplayString
    MAX-ACCESS  read-write
    STATUS      current
    DESCRIPTION
	"The second output name of slave7"
    ::= { slave7OutputDelay 25}
	
slave7OutputDelayTwentysix OBJECT-TYPE
    SYNTAX      DisplayString
    MAX-ACCESS  read-write
    STATUS      current
    DESCRIPTION
	"The second output name of slave7"
    ::= { slave7OutputDelay 26}
	
slave7OutputDelayTwentyseven OBJECT-TYPE
    SYNTAX      DisplayString
    MAX-ACCESS  read-write
    STATUS      current
    DESCRIPTION
	"The second output name of slave7"
    ::= { slave7OutputDelay 27}
	
slave7OutputDelayTwentyeight OBJECT-TYPE
    SYNTAX      DisplayString
    MAX-ACCESS  read-write
    STATUS      current
    DESCRIPTION
	"The second output name of slave7"
    ::= { slave7OutputDelay 28}	
slave7OutputDelayTwentynine OBJECT-TYPE
    SYNTAX      DisplayString
    MAX-ACCESS  read-write
    STATUS      current
    DESCRIPTION
	"The second output name of slave7"
    ::= { slave7OutputDelay 29}
	
slave7OutputDelayThirty OBJECT-TYPE
    SYNTAX      DisplayString
    MAX-ACCESS  read-write
    STATUS      current
    DESCRIPTION
	"The second output name of slave7"
    ::= { slave7OutputDelay 30}
	
slave7OutputDelayThirtyone OBJECT-TYPE
    SYNTAX      DisplayString
    MAX-ACCESS  read-write
    STATUS      current
    DESCRIPTION
	"The second output name of slave7"
    ::= { slave7OutputDelay 31}
	
slave7OutputDelayThirtytwo OBJECT-TYPE
    SYNTAX      DisplayString
    MAX-ACCESS  read-write
    STATUS      current
    DESCRIPTION
	"The second output name of slave7"
    ::= { slave7OutputDelay 32}
	
slave7OutputDelayThirtythree OBJECT-TYPE
    SYNTAX      DisplayString
    MAX-ACCESS  read-write
    STATUS      current
    DESCRIPTION
	"The second output name of slave7"
    ::= { slave7OutputDelay 33}
	
slave7OutputDelayThirtyfour OBJECT-TYPE
    SYNTAX      DisplayString
    MAX-ACCESS  read-write
    STATUS      current
    DESCRIPTION
	"The second output name of slave7"
    ::= { slave7OutputDelay 34}
	
slave7OutputDelayThirtyfive OBJECT-TYPE
    SYNTAX      DisplayString
    MAX-ACCESS  read-write
    STATUS      current
    DESCRIPTION
	"The second output name of slave7"
    ::= { slave7OutputDelay 35}
	
slave7OutputDelayThirtysix OBJECT-TYPE
    SYNTAX      DisplayString
    MAX-ACCESS  read-write
    STATUS      current
    DESCRIPTION
	"The second output name of slave7"
    ::= { slave7OutputDelay 36}
	
slave7OutputDelayThirtyseven OBJECT-TYPE
    SYNTAX      DisplayString
    MAX-ACCESS  read-write
    STATUS      current
    DESCRIPTION
	"The second output name of slave7"
    ::= { slave7OutputDelay 37}
	
slave7OutputDelayThirtyeight OBJECT-TYPE
    SYNTAX      DisplayString
    MAX-ACCESS  read-write
    STATUS      current
    DESCRIPTION
	"The second output name of slave7"
    ::= { slave7OutputDelay 38}
	
slave7OutputDelayThirtynine OBJECT-TYPE
    SYNTAX      DisplayString
    MAX-ACCESS  read-write
    STATUS      current
    DESCRIPTION
	"The second output name of slave7"
    ::= { slave7OutputDelay 39}
	
slave7OutputDelayFourty OBJECT-TYPE
    SYNTAX      DisplayString
    MAX-ACCESS  read-write
    STATUS      current
    DESCRIPTION
	"The second output name of slave7"
    ::= { slave7OutputDelay 40}
	
slave7OutputDelayFourtyone OBJECT-TYPE
    SYNTAX      DisplayString
    MAX-ACCESS  read-write
    STATUS      current
    DESCRIPTION
	"The second output name of slave7"
    ::= { slave7OutputDelay 41}
	
slave7OutputDelayFourtytwo OBJECT-TYPE
    SYNTAX      DisplayString
    MAX-ACCESS  read-write
    STATUS      current
    DESCRIPTION
	"The second output name of slave7"
    ::= { slave7OutputDelay 42}

	
-------------------------------slave7 output switch------------------------	
slave7OutputSwitch OBJECT IDENTIFIER ::= { slave7 7}		
slave7OutputSwitchOne OBJECT-TYPE
    SYNTAX      DisplayString
    MAX-ACCESS  read-write
    STATUS      current
    DESCRIPTION
	"The first output name of slave7"
    ::= { slave7OutputSwitch 1}

slave7OutputSwitchTwo OBJECT-TYPE
    SYNTAX      DisplayString
    MAX-ACCESS  read-write
    STATUS      current
    DESCRIPTION
	"The second output name of slave7"
    ::= { slave7OutputSwitch 2}

slave7OutputSwitchThree OBJECT-TYPE
    SYNTAX      DisplayString
    MAX-ACCESS  read-write
    STATUS      current
    DESCRIPTION
	"The second output name of slave7"
    ::= { slave7OutputSwitch 3}

slave7OutputSwitchFour OBJECT-TYPE
    SYNTAX      DisplayString
    MAX-ACCESS  read-write
    STATUS      current
    DESCRIPTION
	"The second output name of slave7"
    ::= { slave7OutputSwitch 4}

slave7OutputSwitchFive OBJECT-TYPE
    SYNTAX      DisplayString
    MAX-ACCESS  read-write
    STATUS      current
    DESCRIPTION
	"The second output name of slave7"
    ::= { slave7OutputSwitch 5}

slave7OutputSwitchSix OBJECT-TYPE
    SYNTAX      DisplayString
    MAX-ACCESS  read-write
    STATUS      current
    DESCRIPTION
	"The second output name of slave7"
    ::= { slave7OutputSwitch 6}

slave7OutputSwitchSeven OBJECT-TYPE
    SYNTAX      DisplayString
    MAX-ACCESS  read-write
    STATUS      current
    DESCRIPTION
	"The second output name of slave7"
    ::= { slave7OutputSwitch 7}

slave7OutputSwitchEight OBJECT-TYPE
    SYNTAX      DisplayString
    MAX-ACCESS  read-write
    STATUS      current
    DESCRIPTION
	"The second output name of slave7"
    ::= { slave7OutputSwitch 8}

slave7OutputSwitchNine OBJECT-TYPE
    SYNTAX      DisplayString
    MAX-ACCESS  read-write
    STATUS      current
    DESCRIPTION
	"The second output name of slave7"
    ::= { slave7OutputSwitch 9}

slave7OutputSwitchTen OBJECT-TYPE
    SYNTAX      DisplayString
    MAX-ACCESS  read-write
    STATUS      current
    DESCRIPTION
	"The second output name of slave7"
    ::= { slave7OutputSwitch 10}

slave7OutputSwitchEleven OBJECT-TYPE
    SYNTAX      DisplayString
    MAX-ACCESS  read-write
    STATUS      current
    DESCRIPTION
	"The second output name of slave7"
    ::= { slave7OutputSwitch 11}

slave7OutputSwitchTwel OBJECT-TYPE
    SYNTAX      DisplayString
    MAX-ACCESS  read-write
    STATUS      current
    DESCRIPTION
	"The second output name of slave7"
    ::= { slave7OutputSwitch 12}

slave7OutputSwitchThirteen OBJECT-TYPE
    SYNTAX      DisplayString
    MAX-ACCESS  read-write
    STATUS      current
    DESCRIPTION
	"The second output name of slave7"
    ::= { slave7OutputSwitch 13}

slave7OutputSwitchFourteen OBJECT-TYPE
    SYNTAX      DisplayString
    MAX-ACCESS  read-write
    STATUS      current
    DESCRIPTION
	"The second output name of slave7"
    ::= { slave7OutputSwitch 14}

slave7OutputSwitchFifteen OBJECT-TYPE
    SYNTAX      DisplayString
    MAX-ACCESS  read-write
    STATUS      current
    DESCRIPTION
	"The second output name of slave7"
    ::= { slave7OutputSwitch 15}

slave7OutputSwitchSixteen OBJECT-TYPE
    SYNTAX      DisplayString
    MAX-ACCESS  read-write
    STATUS      current
    DESCRIPTION
	"The second output name of slave7"
    ::= { slave7OutputSwitch 16}

slave7OutputSwitchSeventeen OBJECT-TYPE
    SYNTAX      DisplayString
    MAX-ACCESS  read-write
    STATUS      current
    DESCRIPTION
	"The second output name of slave7"
    ::= { slave7OutputSwitch 17}

slave7OutputSwitchEighteen OBJECT-TYPE
    SYNTAX      DisplayString
    MAX-ACCESS  read-write
    STATUS      current
    DESCRIPTION
	"The second output name of slave7"
    ::= { slave7OutputSwitch 18}
	
slave7OutputSwitchNineteen OBJECT-TYPE
    SYNTAX      DisplayString
    MAX-ACCESS  read-write
    STATUS      current
    DESCRIPTION
	"The second output name of slave7"
    ::= { slave7OutputSwitch 19}
	
slave7OutputSwitchtwenty OBJECT-TYPE
    SYNTAX      DisplayString
    MAX-ACCESS  read-write
    STATUS      current
    DESCRIPTION
	"The second output name of slave7"
    ::= { slave7OutputSwitch 20}
	
slave7OutputSwitchTwentyone OBJECT-TYPE
    SYNTAX      DisplayString
    MAX-ACCESS  read-write
    STATUS      current
    DESCRIPTION
	"The second output name of slave7"
    ::= { slave7OutputSwitch 21}
	
slave7OutputSwitchTwentyonetwo OBJECT-TYPE
    SYNTAX      DisplayString
    MAX-ACCESS  read-write
    STATUS      current
    DESCRIPTION
	"The second output name of slave7"
    ::= { slave7OutputSwitch 22}
	
slave7OutputSwitchTwentythree OBJECT-TYPE
    SYNTAX      DisplayString
    MAX-ACCESS  read-write
    STATUS      current
    DESCRIPTION
	"The second output name of slave7"
    ::= { slave7OutputSwitch 23}
	
slave7OutputSwitchTwentyfour OBJECT-TYPE
    SYNTAX      DisplayString
    MAX-ACCESS  read-write
    STATUS      current
    DESCRIPTION
	"The second output name of slave7"
    ::= { slave7OutputSwitch 24}
	
slave7OutputSwitchTwentyfive OBJECT-TYPE
    SYNTAX      DisplayString
    MAX-ACCESS  read-write
    STATUS      current
    DESCRIPTION
	"The second output name of slave7"
    ::= { slave7OutputSwitch 25}
	
slave7OutputSwitchTwentysix OBJECT-TYPE
    SYNTAX      DisplayString
    MAX-ACCESS  read-write
    STATUS      current
    DESCRIPTION
	"The second output name of slave7"
    ::= { slave7OutputSwitch 26}
	
slave7OutputSwitchTwentyseven OBJECT-TYPE
    SYNTAX      DisplayString
    MAX-ACCESS  read-write
    STATUS      current
    DESCRIPTION
	"The second output name of slave7"
    ::= { slave7OutputSwitch 27}
	
slave7OutputSwitchTwentyeight OBJECT-TYPE
    SYNTAX      DisplayString
    MAX-ACCESS  read-write
    STATUS      current
    DESCRIPTION
	"The second output name of slave7"
    ::= { slave7OutputSwitch 28}	
slave7OutputSwitchTwentynine OBJECT-TYPE
    SYNTAX      DisplayString
    MAX-ACCESS  read-write
    STATUS      current
    DESCRIPTION
	"The second output name of slave7"
    ::= { slave7OutputSwitch 29}
	
slave7OutputSwitchThirty OBJECT-TYPE
    SYNTAX      DisplayString
    MAX-ACCESS  read-write
    STATUS      current
    DESCRIPTION
	"The second output name of slave7"
    ::= { slave7OutputSwitch 30}
	
slave7OutputSwitchThirtyone OBJECT-TYPE
    SYNTAX      DisplayString
    MAX-ACCESS  read-write
    STATUS      current
    DESCRIPTION
	"The second output name of slave7"
    ::= { slave7OutputSwitch 31}
	
slave7OutputSwitchThirtytwo OBJECT-TYPE
    SYNTAX      DisplayString
    MAX-ACCESS  read-write
    STATUS      current
    DESCRIPTION
	"The second output name of slave7"
    ::= { slave7OutputSwitch 32}
	
slave7OutputSwitchThirtythree OBJECT-TYPE
    SYNTAX      DisplayString
    MAX-ACCESS  read-write
    STATUS      current
    DESCRIPTION
	"The second output name of slave7"
    ::= { slave7OutputSwitch 33}
	
slave7OutputSwitchThirtyfour OBJECT-TYPE
    SYNTAX      DisplayString
    MAX-ACCESS  read-write
    STATUS      current
    DESCRIPTION
	"The second output name of slave7"
    ::= { slave7OutputSwitch 34}
	
slave7OutputSwitchThirtyfive OBJECT-TYPE
    SYNTAX      DisplayString
    MAX-ACCESS  read-write
    STATUS      current
    DESCRIPTION
	"The second output name of slave7"
    ::= { slave7OutputSwitch 35}
	
slave7OutputSwitchThirtysix OBJECT-TYPE
    SYNTAX      DisplayString
    MAX-ACCESS  read-write
    STATUS      current
    DESCRIPTION
	"The second output name of slave7"
    ::= { slave7OutputSwitch 36}
	
slave7OutputSwitchThirtyseven OBJECT-TYPE
    SYNTAX      DisplayString
    MAX-ACCESS  read-write
    STATUS      current
    DESCRIPTION
	"The second output name of slave7"
    ::= { slave7OutputSwitch 37}
	
slave7OutputSwitchThirtyeight OBJECT-TYPE
    SYNTAX      DisplayString
    MAX-ACCESS  read-write
    STATUS      current
    DESCRIPTION
	"The second output name of slave7"
    ::= { slave7OutputSwitch 38}
	
slave7OutputSwitchThirtynine OBJECT-TYPE
    SYNTAX      DisplayString
    MAX-ACCESS  read-write
    STATUS      current
    DESCRIPTION
	"The second output name of slave7"
    ::= { slave7OutputSwitch 39}
	
slave7OutputSwitchFourty OBJECT-TYPE
    SYNTAX      DisplayString
    MAX-ACCESS  read-write
    STATUS      current
    DESCRIPTION
	"The second output name of slave7"
    ::= { slave7OutputSwitch 40}
	
slave7OutputSwitchFourtyone OBJECT-TYPE
    SYNTAX      DisplayString
    MAX-ACCESS  read-write
    STATUS      current
    DESCRIPTION
	"The second output name of slave7"
    ::= { slave7OutputSwitch 41}
	
slave7OutputSwitchFourtytwo OBJECT-TYPE
    SYNTAX      DisplayString
    MAX-ACCESS  read-write
    STATUS      current
    DESCRIPTION
	"The second output name of slave7"
    ::= { slave7OutputSwitch 42}

	
-------------------------------slave7 output current------------------------	
slave7OutputCurrent OBJECT IDENTIFIER ::= { slave7 8}		
slave7OutputCurrentValue OBJECT IDENTIFIER ::= { slave7OutputCurrent 1}	

slave7OutputCurrentValueOne OBJECT-TYPE
    SYNTAX      DisplayString
    MAX-ACCESS  read-write
    STATUS      current
    DESCRIPTION
	"The first output name of slave7"
    ::= { slave7OutputCurrentValue 1}

slave7OutputCurrentValueTwo OBJECT-TYPE
    SYNTAX      DisplayString
    MAX-ACCESS  read-write
    STATUS      current
    DESCRIPTION
	"The second output name of slave7"
    ::= { slave7OutputCurrentValue 2}

slave7OutputCurrentValueThree OBJECT-TYPE
    SYNTAX      DisplayString
    MAX-ACCESS  read-write
    STATUS      current
    DESCRIPTION
	"The second output name of slave7"
    ::= { slave7OutputCurrentValue 3}

slave7OutputCurrentValueFour OBJECT-TYPE
    SYNTAX      DisplayString
    MAX-ACCESS  read-write
    STATUS      current
    DESCRIPTION
	"The second output name of slave7"
    ::= { slave7OutputCurrentValue 4}

slave7OutputCurrentValueFive OBJECT-TYPE
    SYNTAX      DisplayString
    MAX-ACCESS  read-write
    STATUS      current
    DESCRIPTION
	"The second output name of slave7"
    ::= { slave7OutputCurrentValue 5}

slave7OutputCurrentValueSix OBJECT-TYPE
    SYNTAX      DisplayString
    MAX-ACCESS  read-write
    STATUS      current
    DESCRIPTION
	"The second output name of slave7"
    ::= { slave7OutputCurrentValue 6}

slave7OutputCurrentValueSeven OBJECT-TYPE
    SYNTAX      DisplayString
    MAX-ACCESS  read-write
    STATUS      current
    DESCRIPTION
	"The second output name of slave7"
    ::= { slave7OutputCurrentValue 7}

slave7OutputCurrentValueEight OBJECT-TYPE
    SYNTAX      DisplayString
    MAX-ACCESS  read-write
    STATUS      current
    DESCRIPTION
	"The second output name of slave7"
    ::= { slave7OutputCurrentValue 8}

slave7OutputCurrentValueNine OBJECT-TYPE
    SYNTAX      DisplayString
    MAX-ACCESS  read-write
    STATUS      current
    DESCRIPTION
	"The second output name of slave7"
    ::= { slave7OutputCurrentValue 9}

slave7OutputCurrentValueTen OBJECT-TYPE
    SYNTAX      DisplayString
    MAX-ACCESS  read-write
    STATUS      current
    DESCRIPTION
	"The second output name of slave7"
    ::= { slave7OutputCurrentValue 10}

slave7OutputCurrentValueEleven OBJECT-TYPE
    SYNTAX      DisplayString
    MAX-ACCESS  read-write
    STATUS      current
    DESCRIPTION
	"The second output name of slave7"
    ::= { slave7OutputCurrentValue 11}

slave7OutputCurrentValueTwel OBJECT-TYPE
    SYNTAX      DisplayString
    MAX-ACCESS  read-write
    STATUS      current
    DESCRIPTION
	"The second output name of slave7"
    ::= { slave7OutputCurrentValue 12}

slave7OutputCurrentValueThirteen OBJECT-TYPE
    SYNTAX      DisplayString
    MAX-ACCESS  read-write
    STATUS      current
    DESCRIPTION
	"The second output name of slave7"
    ::= { slave7OutputCurrentValue 13}

slave7OutputCurrentValueFourteen OBJECT-TYPE
    SYNTAX      DisplayString
    MAX-ACCESS  read-write
    STATUS      current
    DESCRIPTION
	"The second output name of slave7"
    ::= { slave7OutputCurrentValue 14}

slave7OutputCurrentValueFifteen OBJECT-TYPE
    SYNTAX      DisplayString
    MAX-ACCESS  read-write
    STATUS      current
    DESCRIPTION
	"The second output name of slave7"
    ::= { slave7OutputCurrentValue 15}

slave7OutputCurrentValueSixteen OBJECT-TYPE
    SYNTAX      DisplayString
    MAX-ACCESS  read-write
    STATUS      current
    DESCRIPTION
	"The second output name of slave7"
    ::= { slave7OutputCurrentValue 16}

slave7OutputCurrentValueSeventeen OBJECT-TYPE
    SYNTAX      DisplayString
    MAX-ACCESS  read-write
    STATUS      current
    DESCRIPTION
	"The second output name of slave7"
    ::= { slave7OutputCurrentValue 17}

slave7OutputCurrentValueEighteen OBJECT-TYPE
    SYNTAX      DisplayString
    MAX-ACCESS  read-write
    STATUS      current
    DESCRIPTION
	"The second output name of slave7"
    ::= { slave7OutputCurrentValue 18}
	
slave7OutputCurrentValueNineteen OBJECT-TYPE
    SYNTAX      DisplayString
    MAX-ACCESS  read-write
    STATUS      current
    DESCRIPTION
	"The second output name of slave7"
    ::= { slave7OutputCurrentValue 19}
	
slave7OutputCurrentValuetwenty OBJECT-TYPE
    SYNTAX      DisplayString
    MAX-ACCESS  read-write
    STATUS      current
    DESCRIPTION
	"The second output name of slave7"
    ::= { slave7OutputCurrentValue 20}
	
slave7OutputCurrentValueTwentyone OBJECT-TYPE
    SYNTAX      DisplayString
    MAX-ACCESS  read-write
    STATUS      current
    DESCRIPTION
	"The second output name of slave7"
    ::= { slave7OutputCurrentValue 21}
	
slave7OutputCurrentValueTwentyonetwo OBJECT-TYPE
    SYNTAX      DisplayString
    MAX-ACCESS  read-write
    STATUS      current
    DESCRIPTION
	"The second output name of slave7"
    ::= { slave7OutputCurrentValue 22}
	
slave7OutputCurrentValueTwentythree OBJECT-TYPE
    SYNTAX      DisplayString
    MAX-ACCESS  read-write
    STATUS      current
    DESCRIPTION
	"The second output name of slave7"
    ::= { slave7OutputCurrentValue 23}
	
slave7OutputCurrentValueTwentyfour OBJECT-TYPE
    SYNTAX      DisplayString
    MAX-ACCESS  read-write
    STATUS      current
    DESCRIPTION
	"The second output name of slave7"
    ::= { slave7OutputCurrentValue 24}
	
slave7OutputCurrentValueTwentyfive OBJECT-TYPE
    SYNTAX      DisplayString
    MAX-ACCESS  read-write
    STATUS      current
    DESCRIPTION
	"The second output name of slave7"
    ::= { slave7OutputCurrentValue 25}
	
slave7OutputCurrentValueTwentysix OBJECT-TYPE
    SYNTAX      DisplayString
    MAX-ACCESS  read-write
    STATUS      current
    DESCRIPTION
	"The second output name of slave7"
    ::= { slave7OutputCurrentValue 26}
	
slave7OutputCurrentValueTwentyseven OBJECT-TYPE
    SYNTAX      DisplayString
    MAX-ACCESS  read-write
    STATUS      current
    DESCRIPTION
	"The second output name of slave7"
    ::= { slave7OutputCurrentValue 27}
	
slave7OutputCurrentValueTwentyeight OBJECT-TYPE
    SYNTAX      DisplayString
    MAX-ACCESS  read-write
    STATUS      current
    DESCRIPTION
	"The second output name of slave7"
    ::= { slave7OutputCurrentValue 28}	
slave7OutputCurrentValueTwentynine OBJECT-TYPE
    SYNTAX      DisplayString
    MAX-ACCESS  read-write
    STATUS      current
    DESCRIPTION
	"The second output name of slave7"
    ::= { slave7OutputCurrentValue 29}
	
slave7OutputCurrentValueThirty OBJECT-TYPE
    SYNTAX      DisplayString
    MAX-ACCESS  read-write
    STATUS      current
    DESCRIPTION
	"The second output name of slave7"
    ::= { slave7OutputCurrentValue 30}
	
slave7OutputCurrentValueThirtyone OBJECT-TYPE
    SYNTAX      DisplayString
    MAX-ACCESS  read-write
    STATUS      current
    DESCRIPTION
	"The second output name of slave7"
    ::= { slave7OutputCurrentValue 31}
	
slave7OutputCurrentValueThirtytwo OBJECT-TYPE
    SYNTAX      DisplayString
    MAX-ACCESS  read-write
    STATUS      current
    DESCRIPTION
	"The second output name of slave7"
    ::= { slave7OutputCurrentValue 32}
	
slave7OutputCurrentValueThirtythree OBJECT-TYPE
    SYNTAX      DisplayString
    MAX-ACCESS  read-write
    STATUS      current
    DESCRIPTION
	"The second output name of slave7"
    ::= { slave7OutputCurrentValue 33}
	
slave7OutputCurrentValueThirtyfour OBJECT-TYPE
    SYNTAX      DisplayString
    MAX-ACCESS  read-write
    STATUS      current
    DESCRIPTION
	"The second output name of slave7"
    ::= { slave7OutputCurrentValue 34}
	
slave7OutputCurrentValueThirtyfive OBJECT-TYPE
    SYNTAX      DisplayString
    MAX-ACCESS  read-write
    STATUS      current
    DESCRIPTION
	"The second output name of slave7"
    ::= { slave7OutputCurrentValue 35}
	
slave7OutputCurrentValueThirtysix OBJECT-TYPE
    SYNTAX      DisplayString
    MAX-ACCESS  read-write
    STATUS      current
    DESCRIPTION
	"The second output name of slave7"
    ::= { slave7OutputCurrentValue 36}
	
slave7OutputCurrentValueThirtyseven OBJECT-TYPE
    SYNTAX      DisplayString
    MAX-ACCESS  read-write
    STATUS      current
    DESCRIPTION
	"The second output name of slave7"
    ::= { slave7OutputCurrentValue 37}
	
slave7OutputCurrentValueThirtyeight OBJECT-TYPE
    SYNTAX      DisplayString
    MAX-ACCESS  read-write
    STATUS      current
    DESCRIPTION
	"The second output name of slave7"
    ::= { slave7OutputCurrentValue 38}
	
slave7OutputCurrentValueThirtynine OBJECT-TYPE
    SYNTAX      DisplayString
    MAX-ACCESS  read-write
    STATUS      current
    DESCRIPTION
	"The second output name of slave7"
    ::= { slave7OutputCurrentValue 39}
	
slave7OutputCurrentValueFourty OBJECT-TYPE
    SYNTAX      DisplayString
    MAX-ACCESS  read-write
    STATUS      current
    DESCRIPTION
	"The second output name of slave7"
    ::= { slave7OutputCurrentValue 40}
	
slave7OutputCurrentValueFourtyone OBJECT-TYPE
    SYNTAX      DisplayString
    MAX-ACCESS  read-write
    STATUS      current
    DESCRIPTION
	"The second output name of slave7"
    ::= { slave7OutputCurrentValue 41}
	
slave7OutputCurrentValueFourtytwo OBJECT-TYPE
    SYNTAX      DisplayString
    MAX-ACCESS  read-write
    STATUS      current
    DESCRIPTION
	"The second output name of slave7"
    ::= { slave7OutputCurrentValue 42}


-------------------------------slave7 output current Min------------------------			
slave7OutputCurrentMin OBJECT IDENTIFIER ::= { slave7OutputCurrent 2}	

slave7OutputCurrentMinOne OBJECT-TYPE
    SYNTAX      DisplayString
    MAX-ACCESS  read-write
    STATUS      current
    DESCRIPTION
	"The first output Min. current alarm value of slave7"
    ::= { slave7OutputCurrentMin 1}

slave7OutputCurrentMinTwo OBJECT-TYPE
    SYNTAX      DisplayString
    MAX-ACCESS  read-write
    STATUS      current
    DESCRIPTION
	"The second output Min. current alarm value of slave7"
    ::= { slave7OutputCurrentMin 2}

slave7OutputCurrentMinThree OBJECT-TYPE
    SYNTAX      DisplayString
    MAX-ACCESS  read-write
    STATUS      current
    DESCRIPTION
	"The second output Min. current alarm value of slave7"
    ::= { slave7OutputCurrentMin 3}

slave7OutputCurrentMinFour OBJECT-TYPE
    SYNTAX      DisplayString
    MAX-ACCESS  read-write
    STATUS      current
    DESCRIPTION
	"The second output Min. current alarm value of slave7"
    ::= { slave7OutputCurrentMin 4}

slave7OutputCurrentMinFive OBJECT-TYPE
    SYNTAX      DisplayString
    MAX-ACCESS  read-write
    STATUS      current
    DESCRIPTION
	"The second output Min. current alarm value of slave7"
    ::= { slave7OutputCurrentMin 5}

slave7OutputCurrentMinSix OBJECT-TYPE
    SYNTAX      DisplayString
    MAX-ACCESS  read-write
    STATUS      current
    DESCRIPTION
	"The second output Min. current alarm value of slave7"
    ::= { slave7OutputCurrentMin 6}

slave7OutputCurrentMinSeven OBJECT-TYPE
    SYNTAX      DisplayString
    MAX-ACCESS  read-write
    STATUS      current
    DESCRIPTION
	"The second output Min. current alarm value of slave7"
    ::= { slave7OutputCurrentMin 7}

slave7OutputCurrentMinEight OBJECT-TYPE
    SYNTAX      DisplayString
    MAX-ACCESS  read-write
    STATUS      current
    DESCRIPTION
	"The second output Min. current alarm value of slave7"
    ::= { slave7OutputCurrentMin 8}

slave7OutputCurrentMinNine OBJECT-TYPE
    SYNTAX      DisplayString
    MAX-ACCESS  read-write
    STATUS      current
    DESCRIPTION
	"The second output Min. current alarm value of slave7"
    ::= { slave7OutputCurrentMin 9}

slave7OutputCurrentMinTen OBJECT-TYPE
    SYNTAX      DisplayString
    MAX-ACCESS  read-write
    STATUS      current
    DESCRIPTION
	"The second output Min. current alarm value of slave7"
    ::= { slave7OutputCurrentMin 10}

slave7OutputCurrentMinEleven OBJECT-TYPE
    SYNTAX      DisplayString
    MAX-ACCESS  read-write
    STATUS      current
    DESCRIPTION
	"The second output Min. current alarm value of slave7"
    ::= { slave7OutputCurrentMin 11}

slave7OutputCurrentMinTwel OBJECT-TYPE
    SYNTAX      DisplayString
    MAX-ACCESS  read-write
    STATUS      current
    DESCRIPTION
	"The second output Min. current alarm value of slave7"
    ::= { slave7OutputCurrentMin 12}

slave7OutputCurrentMinThirteen OBJECT-TYPE
    SYNTAX      DisplayString
    MAX-ACCESS  read-write
    STATUS      current
    DESCRIPTION
	"The second output Min. current alarm value of slave7"
    ::= { slave7OutputCurrentMin 13}

slave7OutputCurrentMinFourteen OBJECT-TYPE
    SYNTAX      DisplayString
    MAX-ACCESS  read-write
    STATUS      current
    DESCRIPTION
	"The second output Min. current alarm value of slave7"
    ::= { slave7OutputCurrentMin 14}

slave7OutputCurrentMinFifteen OBJECT-TYPE
    SYNTAX      DisplayString
    MAX-ACCESS  read-write
    STATUS      current
    DESCRIPTION
	"The second output Min. current alarm value of slave7"
    ::= { slave7OutputCurrentMin 15}

slave7OutputCurrentMinSixteen OBJECT-TYPE
    SYNTAX      DisplayString
    MAX-ACCESS  read-write
    STATUS      current
    DESCRIPTION
	"The second output Min. current alarm value of slave7"
    ::= { slave7OutputCurrentMin 16}

slave7OutputCurrentMinSeventeen OBJECT-TYPE
    SYNTAX      DisplayString
    MAX-ACCESS  read-write
    STATUS      current
    DESCRIPTION
	"The second output Min. current alarm value of slave7"
    ::= { slave7OutputCurrentMin 17}

slave7OutputCurrentMinEighteen OBJECT-TYPE
    SYNTAX      DisplayString
    MAX-ACCESS  read-write
    STATUS      current
    DESCRIPTION
	"The second output Min. current alarm value of slave7"
    ::= { slave7OutputCurrentMin 18}
	
slave7OutputCurrentMinNineteen OBJECT-TYPE
    SYNTAX      DisplayString
    MAX-ACCESS  read-write
    STATUS      current
    DESCRIPTION
	"The second output Min. current alarm value of slave7"
    ::= { slave7OutputCurrentMin 19}
	
slave7OutputCurrentMintwenty OBJECT-TYPE
    SYNTAX      DisplayString
    MAX-ACCESS  read-write
    STATUS      current
    DESCRIPTION
	"The second output Min. current alarm value of slave7"
    ::= { slave7OutputCurrentMin 20}
	
slave7OutputCurrentMinTwentyone OBJECT-TYPE
    SYNTAX      DisplayString
    MAX-ACCESS  read-write
    STATUS      current
    DESCRIPTION
	"The second output Min. current alarm value of slave7"
    ::= { slave7OutputCurrentMin 21}
	
slave7OutputCurrentMinTwentyonetwo OBJECT-TYPE
    SYNTAX      DisplayString
    MAX-ACCESS  read-write
    STATUS      current
    DESCRIPTION
	"The second output Min. current alarm value of slave7"
    ::= { slave7OutputCurrentMin 22}
	
slave7OutputCurrentMinTwentythree OBJECT-TYPE
    SYNTAX      DisplayString
    MAX-ACCESS  read-write
    STATUS      current
    DESCRIPTION
	"The second output Min. current alarm value of slave7"
    ::= { slave7OutputCurrentMin 23}
	
slave7OutputCurrentMinTwentyfour OBJECT-TYPE
    SYNTAX      DisplayString
    MAX-ACCESS  read-write
    STATUS      current
    DESCRIPTION
	"The second output Min. current alarm value of slave7"
    ::= { slave7OutputCurrentMin 24}
	
slave7OutputCurrentMinTwentyfive OBJECT-TYPE
    SYNTAX      DisplayString
    MAX-ACCESS  read-write
    STATUS      current
    DESCRIPTION
	"The second output Min. current alarm value of slave7"
    ::= { slave7OutputCurrentMin 25}
	
slave7OutputCurrentMinTwentysix OBJECT-TYPE
    SYNTAX      DisplayString
    MAX-ACCESS  read-write
    STATUS      current
    DESCRIPTION
	"The second output Min. current alarm value of slave7"
    ::= { slave7OutputCurrentMin 26}
	
slave7OutputCurrentMinTwentyseven OBJECT-TYPE
    SYNTAX      DisplayString
    MAX-ACCESS  read-write
    STATUS      current
    DESCRIPTION
	"The second output Min. current alarm value of slave7"
    ::= { slave7OutputCurrentMin 27}
	
slave7OutputCurrentMinTwentyeight OBJECT-TYPE
    SYNTAX      DisplayString
    MAX-ACCESS  read-write
    STATUS      current
    DESCRIPTION
	"The second output Min. current alarm value of slave7"
    ::= { slave7OutputCurrentMin 28}	
slave7OutputCurrentMinTwentynine OBJECT-TYPE
    SYNTAX      DisplayString
    MAX-ACCESS  read-write
    STATUS      current
    DESCRIPTION
	"The second output Min. current alarm value of slave7"
    ::= { slave7OutputCurrentMin 29}
	
slave7OutputCurrentMinThirty OBJECT-TYPE
    SYNTAX      DisplayString
    MAX-ACCESS  read-write
    STATUS      current
    DESCRIPTION
	"The second output Min. current alarm value of slave7"
    ::= { slave7OutputCurrentMin 30}
	
slave7OutputCurrentMinThirtyone OBJECT-TYPE
    SYNTAX      DisplayString
    MAX-ACCESS  read-write
    STATUS      current
    DESCRIPTION
	"The second output Min. current alarm value of slave7"
    ::= { slave7OutputCurrentMin 31}
	
slave7OutputCurrentMinThirtytwo OBJECT-TYPE
    SYNTAX      DisplayString
    MAX-ACCESS  read-write
    STATUS      current
    DESCRIPTION
	"The second output Min. current alarm value of slave7"
    ::= { slave7OutputCurrentMin 32}
	
slave7OutputCurrentMinThirtythree OBJECT-TYPE
    SYNTAX      DisplayString
    MAX-ACCESS  read-write
    STATUS      current
    DESCRIPTION
	"The second output Min. current alarm value of slave7"
    ::= { slave7OutputCurrentMin 33}
	
slave7OutputCurrentMinThirtyfour OBJECT-TYPE
    SYNTAX      DisplayString
    MAX-ACCESS  read-write
    STATUS      current
    DESCRIPTION
	"The second output Min. current alarm value of slave7"
    ::= { slave7OutputCurrentMin 34}
	
slave7OutputCurrentMinThirtyfive OBJECT-TYPE
    SYNTAX      DisplayString
    MAX-ACCESS  read-write
    STATUS      current
    DESCRIPTION
	"The second output Min. current alarm value of slave7"
    ::= { slave7OutputCurrentMin 35}
	
slave7OutputCurrentMinThirtysix OBJECT-TYPE
    SYNTAX      DisplayString
    MAX-ACCESS  read-write
    STATUS      current
    DESCRIPTION
	"The second output Min. current alarm value of slave7"
    ::= { slave7OutputCurrentMin 36}
	
slave7OutputCurrentMinThirtyseven OBJECT-TYPE
    SYNTAX      DisplayString
    MAX-ACCESS  read-write
    STATUS      current
    DESCRIPTION
	"The second output Min. current alarm value of slave7"
    ::= { slave7OutputCurrentMin 37}
	
slave7OutputCurrentMinThirtyeight OBJECT-TYPE
    SYNTAX      DisplayString
    MAX-ACCESS  read-write
    STATUS      current
    DESCRIPTION
	"The second output Min. current alarm value of slave7"
    ::= { slave7OutputCurrentMin 38}
	
slave7OutputCurrentMinThirtynine OBJECT-TYPE
    SYNTAX      DisplayString
    MAX-ACCESS  read-write
    STATUS      current
    DESCRIPTION
	"The second output Min. current alarm value of slave7"
    ::= { slave7OutputCurrentMin 39}
	
slave7OutputCurrentMinFourty OBJECT-TYPE
    SYNTAX      DisplayString
    MAX-ACCESS  read-write
    STATUS      current
    DESCRIPTION
	"The second output Min. current alarm value of slave7"
    ::= { slave7OutputCurrentMin 40}
	
slave7OutputCurrentMinFourtyone OBJECT-TYPE
    SYNTAX      DisplayString
    MAX-ACCESS  read-write
    STATUS      current
    DESCRIPTION
	"The second output Min. current alarm value of slave7"
    ::= { slave7OutputCurrentMin 41}
	
slave7OutputCurrentMinFourtytwo OBJECT-TYPE
    SYNTAX      DisplayString
    MAX-ACCESS  read-write
    STATUS      current
    DESCRIPTION
	"The second output Min. current alarm value of slave7"
    ::= { slave7OutputCurrentMin 42}


------------------------slave7 output current Min critical----------------			
slave7OutputCurrentMinCritical OBJECT IDENTIFIER ::= { slave7OutputCurrent 3}	

slave7OutputCurrentMinCriticalOne OBJECT-TYPE
    SYNTAX      DisplayString
    MAX-ACCESS  read-write
    STATUS      current
    DESCRIPTION
	"The first output Min. current warning value of slave7"
    ::= { slave7OutputCurrentMinCritical 1}

slave7OutputCurrentMinCriticalTwo OBJECT-TYPE
    SYNTAX      DisplayString
    MAX-ACCESS  read-write
    STATUS      current
    DESCRIPTION
	"The second output Min. current warning value of slave7"
    ::= { slave7OutputCurrentMinCritical 2}

slave7OutputCurrentMinCriticalThree OBJECT-TYPE
    SYNTAX      DisplayString
    MAX-ACCESS  read-write
    STATUS      current
    DESCRIPTION
	"The second output Min. current warning value of slave7"
    ::= { slave7OutputCurrentMinCritical 3}

slave7OutputCurrentMinCriticalFour OBJECT-TYPE
    SYNTAX      DisplayString
    MAX-ACCESS  read-write
    STATUS      current
    DESCRIPTION
	"The second output Min. current warning value of slave7"
    ::= { slave7OutputCurrentMinCritical 4}

slave7OutputCurrentMinCriticalFive OBJECT-TYPE
    SYNTAX      DisplayString
    MAX-ACCESS  read-write
    STATUS      current
    DESCRIPTION
	"The second output Min. current warning value of slave7"
    ::= { slave7OutputCurrentMinCritical 5}

slave7OutputCurrentMinCriticalSix OBJECT-TYPE
    SYNTAX      DisplayString
    MAX-ACCESS  read-write
    STATUS      current
    DESCRIPTION
	"The second output Min. current warning value of slave7"
    ::= { slave7OutputCurrentMinCritical 6}

slave7OutputCurrentMinCriticalSeven OBJECT-TYPE
    SYNTAX      DisplayString
    MAX-ACCESS  read-write
    STATUS      current
    DESCRIPTION
	"The second output Min. current warning value of slave7"
    ::= { slave7OutputCurrentMinCritical 7}

slave7OutputCurrentMinCriticalEight OBJECT-TYPE
    SYNTAX      DisplayString
    MAX-ACCESS  read-write
    STATUS      current
    DESCRIPTION
	"The second output Min. current warning value of slave7"
    ::= { slave7OutputCurrentMinCritical 8}

slave7OutputCurrentMinCriticalNine OBJECT-TYPE
    SYNTAX      DisplayString
    MAX-ACCESS  read-write
    STATUS      current
    DESCRIPTION
	"The second output Min. current warning value of slave7"
    ::= { slave7OutputCurrentMinCritical 9}

slave7OutputCurrentMinCriticalTen OBJECT-TYPE
    SYNTAX      DisplayString
    MAX-ACCESS  read-write
    STATUS      current
    DESCRIPTION
	"The second output Min. current warning value of slave7"
    ::= { slave7OutputCurrentMinCritical 10}

slave7OutputCurrentMinCriticalEleven OBJECT-TYPE
    SYNTAX      DisplayString
    MAX-ACCESS  read-write
    STATUS      current
    DESCRIPTION
	"The second output Min. current warning value of slave7"
    ::= { slave7OutputCurrentMinCritical 11}

slave7OutputCurrentMinCriticalTwel OBJECT-TYPE
    SYNTAX      DisplayString
    MAX-ACCESS  read-write
    STATUS      current
    DESCRIPTION
	"The second output Min. current warning value of slave7"
    ::= { slave7OutputCurrentMinCritical 12}

slave7OutputCurrentMinCriticalThirteen OBJECT-TYPE
    SYNTAX      DisplayString
    MAX-ACCESS  read-write
    STATUS      current
    DESCRIPTION
	"The second output Min. current warning value of slave7"
    ::= { slave7OutputCurrentMinCritical 13}

slave7OutputCurrentMinCriticalFourteen OBJECT-TYPE
    SYNTAX      DisplayString
    MAX-ACCESS  read-write
    STATUS      current
    DESCRIPTION
	"The second output Min. current warning value of slave7"
    ::= { slave7OutputCurrentMinCritical 14}

slave7OutputCurrentMinCriticalFifteen OBJECT-TYPE
    SYNTAX      DisplayString
    MAX-ACCESS  read-write
    STATUS      current
    DESCRIPTION
	"The second output Min. current warning value of slave7"
    ::= { slave7OutputCurrentMinCritical 15}

slave7OutputCurrentMinCriticalSixteen OBJECT-TYPE
    SYNTAX      DisplayString
    MAX-ACCESS  read-write
    STATUS      current
    DESCRIPTION
	"The second output Min. current warning value of slave7"
    ::= { slave7OutputCurrentMinCritical 16}

slave7OutputCurrentMinCriticalSeventeen OBJECT-TYPE
    SYNTAX      DisplayString
    MAX-ACCESS  read-write
    STATUS      current
    DESCRIPTION
	"The second output Min. current warning value of slave7"
    ::= { slave7OutputCurrentMinCritical 17}

slave7OutputCurrentMinCriticalEighteen OBJECT-TYPE
    SYNTAX      DisplayString
    MAX-ACCESS  read-write
    STATUS      current
    DESCRIPTION
	"The second output Min. current warning value of slave7"
    ::= { slave7OutputCurrentMinCritical 18}
	
slave7OutputCurrentMinCriticalNineteen OBJECT-TYPE
    SYNTAX      DisplayString
    MAX-ACCESS  read-write
    STATUS      current
    DESCRIPTION
	"The second output Min. current warning value of slave7"
    ::= { slave7OutputCurrentMinCritical 19}
	
slave7OutputCurrentMinCriticaltwenty OBJECT-TYPE
    SYNTAX      DisplayString
    MAX-ACCESS  read-write
    STATUS      current
    DESCRIPTION
	"The second output Min. current warning value of slave7"
    ::= { slave7OutputCurrentMinCritical 20}
	
slave7OutputCurrentMinCriticalTwentyone OBJECT-TYPE
    SYNTAX      DisplayString
    MAX-ACCESS  read-write
    STATUS      current
    DESCRIPTION
	"The second output Min. current warning value of slave7"
    ::= { slave7OutputCurrentMinCritical 21}
	
slave7OutputCurrentMinCriticalTwentyonetwo OBJECT-TYPE
    SYNTAX      DisplayString
    MAX-ACCESS  read-write
    STATUS      current
    DESCRIPTION
	"The second output Min. current warning value of slave7"
    ::= { slave7OutputCurrentMinCritical 22}
	
slave7OutputCurrentMinCriticalTwentythree OBJECT-TYPE
    SYNTAX      DisplayString
    MAX-ACCESS  read-write
    STATUS      current
    DESCRIPTION
	"The second output Min. current warning value of slave7"
    ::= { slave7OutputCurrentMinCritical 23}
	
slave7OutputCurrentMinCriticalTwentyfour OBJECT-TYPE
    SYNTAX      DisplayString
    MAX-ACCESS  read-write
    STATUS      current
    DESCRIPTION
	"The second output Min. current warning value of slave7"
    ::= { slave7OutputCurrentMinCritical 24}
	
slave7OutputCurrentMinCriticalTwentyfive OBJECT-TYPE
    SYNTAX      DisplayString
    MAX-ACCESS  read-write
    STATUS      current
    DESCRIPTION
	"The second output Min. current warning value of slave7"
    ::= { slave7OutputCurrentMinCritical 25}
	
slave7OutputCurrentMinCriticalTwentysix OBJECT-TYPE
    SYNTAX      DisplayString
    MAX-ACCESS  read-write
    STATUS      current
    DESCRIPTION
	"The second output Min. current warning value of slave7"
    ::= { slave7OutputCurrentMinCritical 26}
	
slave7OutputCurrentMinCriticalTwentyseven OBJECT-TYPE
    SYNTAX      DisplayString
    MAX-ACCESS  read-write
    STATUS      current
    DESCRIPTION
	"The second output Min. current warning value of slave7"
    ::= { slave7OutputCurrentMinCritical 27}
	
slave7OutputCurrentMinCriticalTwentyeight OBJECT-TYPE
    SYNTAX      DisplayString
    MAX-ACCESS  read-write
    STATUS      current
    DESCRIPTION
	"The second output Min. current warning value of slave7"
    ::= { slave7OutputCurrentMinCritical 28}	
slave7OutputCurrentMinCriticalTwentynine OBJECT-TYPE
    SYNTAX      DisplayString
    MAX-ACCESS  read-write
    STATUS      current
    DESCRIPTION
	"The second output Min. current warning value of slave7"
    ::= { slave7OutputCurrentMinCritical 29}
	
slave7OutputCurrentMinCriticalThirty OBJECT-TYPE
    SYNTAX      DisplayString
    MAX-ACCESS  read-write
    STATUS      current
    DESCRIPTION
	"The second output Min. current warning value of slave7"
    ::= { slave7OutputCurrentMinCritical 30}
	
slave7OutputCurrentMinCriticalThirtyone OBJECT-TYPE
    SYNTAX      DisplayString
    MAX-ACCESS  read-write
    STATUS      current
    DESCRIPTION
	"The second output Min. current warning value of slave7"
    ::= { slave7OutputCurrentMinCritical 31}
	
slave7OutputCurrentMinCriticalThirtytwo OBJECT-TYPE
    SYNTAX      DisplayString
    MAX-ACCESS  read-write
    STATUS      current
    DESCRIPTION
	"The second output Min. current warning value of slave7"
    ::= { slave7OutputCurrentMinCritical 32}
	
slave7OutputCurrentMinCriticalThirtythree OBJECT-TYPE
    SYNTAX      DisplayString
    MAX-ACCESS  read-write
    STATUS      current
    DESCRIPTION
	"The second output Min. current warning value of slave7"
    ::= { slave7OutputCurrentMinCritical 33}
	
slave7OutputCurrentMinCriticalThirtyfour OBJECT-TYPE
    SYNTAX      DisplayString
    MAX-ACCESS  read-write
    STATUS      current
    DESCRIPTION
	"The second output Min. current warning value of slave7"
    ::= { slave7OutputCurrentMinCritical 34}
	
slave7OutputCurrentMinCriticalThirtyfive OBJECT-TYPE
    SYNTAX      DisplayString
    MAX-ACCESS  read-write
    STATUS      current
    DESCRIPTION
	"The second output Min. current warning value of slave7"
    ::= { slave7OutputCurrentMinCritical 35}
	
slave7OutputCurrentMinCriticalThirtysix OBJECT-TYPE
    SYNTAX      DisplayString
    MAX-ACCESS  read-write
    STATUS      current
    DESCRIPTION
	"The second output Min. current warning value of slave7"
    ::= { slave7OutputCurrentMinCritical 36}
	
slave7OutputCurrentMinCriticalThirtyseven OBJECT-TYPE
    SYNTAX      DisplayString
    MAX-ACCESS  read-write
    STATUS      current
    DESCRIPTION
	"The second output Min. current warning value of slave7"
    ::= { slave7OutputCurrentMinCritical 37}
	
slave7OutputCurrentMinCriticalThirtyeight OBJECT-TYPE
    SYNTAX      DisplayString
    MAX-ACCESS  read-write
    STATUS      current
    DESCRIPTION
	"The second output Min. current warning value of slave7"
    ::= { slave7OutputCurrentMinCritical 38}
	
slave7OutputCurrentMinCriticalThirtynine OBJECT-TYPE
    SYNTAX      DisplayString
    MAX-ACCESS  read-write
    STATUS      current
    DESCRIPTION
	"The second output Min. current warning value of slave7"
    ::= { slave7OutputCurrentMinCritical 39}
	
slave7OutputCurrentMinCriticalFourty OBJECT-TYPE
    SYNTAX      DisplayString
    MAX-ACCESS  read-write
    STATUS      current
    DESCRIPTION
	"The second output Min. current warning value of slave7"
    ::= { slave7OutputCurrentMinCritical 40}
	
slave7OutputCurrentMinCriticalFourtyone OBJECT-TYPE
    SYNTAX      DisplayString
    MAX-ACCESS  read-write
    STATUS      current
    DESCRIPTION
	"The second output Min. current warning value of slave7"
    ::= { slave7OutputCurrentMinCritical 41}
	
slave7OutputCurrentMinCriticalFourtytwo OBJECT-TYPE
    SYNTAX      DisplayString
    MAX-ACCESS  read-write
    STATUS      current
    DESCRIPTION
	"The second output Min. current warning value of slave7"
    ::= { slave7OutputCurrentMinCritical 42}
	
	
------------------------slave7 output current Max critical----------------			
slave7OutputCurrentMaxCritical OBJECT IDENTIFIER ::= { slave7OutputCurrent 4}	

slave7OutputCurrentMaxCriticalOne OBJECT-TYPE
    SYNTAX      DisplayString
    MAX-ACCESS  read-write
    STATUS      current
    DESCRIPTION
	"The first output Max. current warning value of slave7"
    ::= { slave7OutputCurrentMaxCritical 1}

slave7OutputCurrentMaxCriticalTwo OBJECT-TYPE
    SYNTAX      DisplayString
    MAX-ACCESS  read-write
    STATUS      current
    DESCRIPTION
	"The second output Max. current warning value of slave7"
    ::= { slave7OutputCurrentMaxCritical 2}

slave7OutputCurrentMaxCriticalThree OBJECT-TYPE
    SYNTAX      DisplayString
    MAX-ACCESS  read-write
    STATUS      current
    DESCRIPTION
	"The second output Max. current warning value of slave7"
    ::= { slave7OutputCurrentMaxCritical 3}

slave7OutputCurrentMaxCriticalFour OBJECT-TYPE
    SYNTAX      DisplayString
    MAX-ACCESS  read-write
    STATUS      current
    DESCRIPTION
	"The second output Max. current warning value of slave7"
    ::= { slave7OutputCurrentMaxCritical 4}

slave7OutputCurrentMaxCriticalFive OBJECT-TYPE
    SYNTAX      DisplayString
    MAX-ACCESS  read-write
    STATUS      current
    DESCRIPTION
	"The second output Max. current warning value of slave7"
    ::= { slave7OutputCurrentMaxCritical 5}

slave7OutputCurrentMaxCriticalSix OBJECT-TYPE
    SYNTAX      DisplayString
    MAX-ACCESS  read-write
    STATUS      current
    DESCRIPTION
	"The second output Max. current warning value of slave7"
    ::= { slave7OutputCurrentMaxCritical 6}

slave7OutputCurrentMaxCriticalSeven OBJECT-TYPE
    SYNTAX      DisplayString
    MAX-ACCESS  read-write
    STATUS      current
    DESCRIPTION
	"The second output Max. current warning value of slave7"
    ::= { slave7OutputCurrentMaxCritical 7}

slave7OutputCurrentMaxCriticalEight OBJECT-TYPE
    SYNTAX      DisplayString
    MAX-ACCESS  read-write
    STATUS      current
    DESCRIPTION
	"The second output Max. current warning value of slave7"
    ::= { slave7OutputCurrentMaxCritical 8}

slave7OutputCurrentMaxCriticalNine OBJECT-TYPE
    SYNTAX      DisplayString
    MAX-ACCESS  read-write
    STATUS      current
    DESCRIPTION
	"The second output Max. current warning value of slave7"
    ::= { slave7OutputCurrentMaxCritical 9}

slave7OutputCurrentMaxCriticalTen OBJECT-TYPE
    SYNTAX      DisplayString
    MAX-ACCESS  read-write
    STATUS      current
    DESCRIPTION
	"The second output Max. current warning value of slave7"
    ::= { slave7OutputCurrentMaxCritical 10}

slave7OutputCurrentMaxCriticalEleven OBJECT-TYPE
    SYNTAX      DisplayString
    MAX-ACCESS  read-write
    STATUS      current
    DESCRIPTION
	"The second output Max. current warning value of slave7"
    ::= { slave7OutputCurrentMaxCritical 11}

slave7OutputCurrentMaxCriticalTwel OBJECT-TYPE
    SYNTAX      DisplayString
    MAX-ACCESS  read-write
    STATUS      current
    DESCRIPTION
	"The second output Max. current warning value of slave7"
    ::= { slave7OutputCurrentMaxCritical 12}

slave7OutputCurrentMaxCriticalThirteen OBJECT-TYPE
    SYNTAX      DisplayString
    MAX-ACCESS  read-write
    STATUS      current
    DESCRIPTION
	"The second output Max. current warning value of slave7"
    ::= { slave7OutputCurrentMaxCritical 13}

slave7OutputCurrentMaxCriticalFourteen OBJECT-TYPE
    SYNTAX      DisplayString
    MAX-ACCESS  read-write
    STATUS      current
    DESCRIPTION
	"The second output Max. current warning value of slave7"
    ::= { slave7OutputCurrentMaxCritical 14}

slave7OutputCurrentMaxCriticalFifteen OBJECT-TYPE
    SYNTAX      DisplayString
    MAX-ACCESS  read-write
    STATUS      current
    DESCRIPTION
	"The second output Max. current warning value of slave7"
    ::= { slave7OutputCurrentMaxCritical 15}

slave7OutputCurrentMaxCriticalSixteen OBJECT-TYPE
    SYNTAX      DisplayString
    MAX-ACCESS  read-write
    STATUS      current
    DESCRIPTION
	"The second output Max. current warning value of slave7"
    ::= { slave7OutputCurrentMaxCritical 16}

slave7OutputCurrentMaxCriticalSeventeen OBJECT-TYPE
    SYNTAX      DisplayString
    MAX-ACCESS  read-write
    STATUS      current
    DESCRIPTION
	"The second output Max. current warning value of slave7"
    ::= { slave7OutputCurrentMaxCritical 17}

slave7OutputCurrentMaxCriticalEighteen OBJECT-TYPE
    SYNTAX      DisplayString
    MAX-ACCESS  read-write
    STATUS      current
    DESCRIPTION
	"The second output Max. current warning value of slave7"
    ::= { slave7OutputCurrentMaxCritical 18}
	
slave7OutputCurrentMaxCriticalNineteen OBJECT-TYPE
    SYNTAX      DisplayString
    MAX-ACCESS  read-write
    STATUS      current
    DESCRIPTION
	"The second output Max. current warning value of slave7"
    ::= { slave7OutputCurrentMaxCritical 19}
	
slave7OutputCurrentMaxCriticaltwenty OBJECT-TYPE
    SYNTAX      DisplayString
    MAX-ACCESS  read-write
    STATUS      current
    DESCRIPTION
	"The second output Max. current warning value of slave7"
    ::= { slave7OutputCurrentMaxCritical 20}
	
slave7OutputCurrentMaxCriticalTwentyone OBJECT-TYPE
    SYNTAX      DisplayString
    MAX-ACCESS  read-write
    STATUS      current
    DESCRIPTION
	"The second output Max. current warning value of slave7"
    ::= { slave7OutputCurrentMaxCritical 21}
	
slave7OutputCurrentMaxCriticalTwentyonetwo OBJECT-TYPE
    SYNTAX      DisplayString
    MAX-ACCESS  read-write
    STATUS      current
    DESCRIPTION
	"The second output Max. current warning value of slave7"
    ::= { slave7OutputCurrentMaxCritical 22}
	
slave7OutputCurrentMaxCriticalTwentythree OBJECT-TYPE
    SYNTAX      DisplayString
    MAX-ACCESS  read-write
    STATUS      current
    DESCRIPTION
	"The second output Max. current warning value of slave7"
    ::= { slave7OutputCurrentMaxCritical 23}
	
slave7OutputCurrentMaxCriticalTwentyfour OBJECT-TYPE
    SYNTAX      DisplayString
    MAX-ACCESS  read-write
    STATUS      current
    DESCRIPTION
	"The second output Max. current warning value of slave7"
    ::= { slave7OutputCurrentMaxCritical 24}
	
slave7OutputCurrentMaxCriticalTwentyfive OBJECT-TYPE
    SYNTAX      DisplayString
    MAX-ACCESS  read-write
    STATUS      current
    DESCRIPTION
	"The second output Max. current warning value of slave7"
    ::= { slave7OutputCurrentMaxCritical 25}
	
slave7OutputCurrentMaxCriticalTwentysix OBJECT-TYPE
    SYNTAX      DisplayString
    MAX-ACCESS  read-write
    STATUS      current
    DESCRIPTION
	"The second output Max. current warning value of slave7"
    ::= { slave7OutputCurrentMaxCritical 26}
	
slave7OutputCurrentMaxCriticalTwentyseven OBJECT-TYPE
    SYNTAX      DisplayString
    MAX-ACCESS  read-write
    STATUS      current
    DESCRIPTION
	"The second output Max. current warning value of slave7"
    ::= { slave7OutputCurrentMaxCritical 27}
	
slave7OutputCurrentMaxCriticalTwentyeight OBJECT-TYPE
    SYNTAX      DisplayString
    MAX-ACCESS  read-write
    STATUS      current
    DESCRIPTION
	"The second output Max. current warning value of slave7"
    ::= { slave7OutputCurrentMaxCritical 28}	
slave7OutputCurrentMaxCriticalTwentynine OBJECT-TYPE
    SYNTAX      DisplayString
    MAX-ACCESS  read-write
    STATUS      current
    DESCRIPTION
	"The second output Max. current warning value of slave7"
    ::= { slave7OutputCurrentMaxCritical 29}
	
slave7OutputCurrentMaxCriticalThirty OBJECT-TYPE
    SYNTAX      DisplayString
    MAX-ACCESS  read-write
    STATUS      current
    DESCRIPTION
	"The second output Max. current warning value of slave7"
    ::= { slave7OutputCurrentMaxCritical 30}
	
slave7OutputCurrentMaxCriticalThirtyone OBJECT-TYPE
    SYNTAX      DisplayString
    MAX-ACCESS  read-write
    STATUS      current
    DESCRIPTION
	"The second output Max. current warning value of slave7"
    ::= { slave7OutputCurrentMaxCritical 31}
	
slave7OutputCurrentMaxCriticalThirtytwo OBJECT-TYPE
    SYNTAX      DisplayString
    MAX-ACCESS  read-write
    STATUS      current
    DESCRIPTION
	"The second output Max. current warning value of slave7"
    ::= { slave7OutputCurrentMaxCritical 32}
	
slave7OutputCurrentMaxCriticalThirtythree OBJECT-TYPE
    SYNTAX      DisplayString
    MAX-ACCESS  read-write
    STATUS      current
    DESCRIPTION
	"The second output Max. current warning value of slave7"
    ::= { slave7OutputCurrentMaxCritical 33}
	
slave7OutputCurrentMaxCriticalThirtyfour OBJECT-TYPE
    SYNTAX      DisplayString
    MAX-ACCESS  read-write
    STATUS      current
    DESCRIPTION
	"The second output Max. current warning value of slave7"
    ::= { slave7OutputCurrentMaxCritical 34}
	
slave7OutputCurrentMaxCriticalThirtyfive OBJECT-TYPE
    SYNTAX      DisplayString
    MAX-ACCESS  read-write
    STATUS      current
    DESCRIPTION
	"The second output Max. current warning value of slave7"
    ::= { slave7OutputCurrentMaxCritical 35}
	
slave7OutputCurrentMaxCriticalThirtysix OBJECT-TYPE
    SYNTAX      DisplayString
    MAX-ACCESS  read-write
    STATUS      current
    DESCRIPTION
	"The second output Max. current warning value of slave7"
    ::= { slave7OutputCurrentMaxCritical 36}
	
slave7OutputCurrentMaxCriticalThirtyseven OBJECT-TYPE
    SYNTAX      DisplayString
    MAX-ACCESS  read-write
    STATUS      current
    DESCRIPTION
	"The second output Max. current warning value of slave7"
    ::= { slave7OutputCurrentMaxCritical 37}
	
slave7OutputCurrentMaxCriticalThirtyeight OBJECT-TYPE
    SYNTAX      DisplayString
    MAX-ACCESS  read-write
    STATUS      current
    DESCRIPTION
	"The second output Max. current warning value of slave7"
    ::= { slave7OutputCurrentMaxCritical 38}
	
slave7OutputCurrentMaxCriticalThirtynine OBJECT-TYPE
    SYNTAX      DisplayString
    MAX-ACCESS  read-write
    STATUS      current
    DESCRIPTION
	"The second output Max. current warning value of slave7"
    ::= { slave7OutputCurrentMaxCritical 39}
	
slave7OutputCurrentMaxCriticalFourty OBJECT-TYPE
    SYNTAX      DisplayString
    MAX-ACCESS  read-write
    STATUS      current
    DESCRIPTION
	"The second output Max. current warning value of slave7"
    ::= { slave7OutputCurrentMaxCritical 40}
	
slave7OutputCurrentMaxCriticalFourtyone OBJECT-TYPE
    SYNTAX      DisplayString
    MAX-ACCESS  read-write
    STATUS      current
    DESCRIPTION
	"The second output Max. current warning value of slave7"
    ::= { slave7OutputCurrentMaxCritical 41}
	
slave7OutputCurrentMaxCriticalFourtytwo OBJECT-TYPE
    SYNTAX      DisplayString
    MAX-ACCESS  read-write
    STATUS      current
    DESCRIPTION
	"The second output Max. current warning value of slave7"
    ::= { slave7OutputCurrentMaxCritical 42}
	
	
------------------------slave7 output current Max----------------			
slave7OutputCurrentMax OBJECT IDENTIFIER ::= { slave7OutputCurrent 5}
	
slave7OutputCurrentMaxOne OBJECT-TYPE
    SYNTAX      DisplayString
    MAX-ACCESS  read-write
    STATUS      current
    DESCRIPTION
	"The first output Max. current alarm value of slave7"
    ::= { slave7OutputCurrentMax 1}

slave7OutputCurrentMaxTwo OBJECT-TYPE
    SYNTAX      DisplayString
    MAX-ACCESS  read-write
    STATUS      current
    DESCRIPTION
	"The second output Max. current alarm value of slave7"
    ::= { slave7OutputCurrentMax 2}

slave7OutputCurrentMaxThree OBJECT-TYPE
    SYNTAX      DisplayString
    MAX-ACCESS  read-write
    STATUS      current
    DESCRIPTION
	"The second output Max. current alarm value of slave7"
    ::= { slave7OutputCurrentMax 3}

slave7OutputCurrentMaxFour OBJECT-TYPE
    SYNTAX      DisplayString
    MAX-ACCESS  read-write
    STATUS      current
    DESCRIPTION
	"The second output Max. current alarm value of slave7"
    ::= { slave7OutputCurrentMax 4}

slave7OutputCurrentMaxFive OBJECT-TYPE
    SYNTAX      DisplayString
    MAX-ACCESS  read-write
    STATUS      current
    DESCRIPTION
	"The second output Max. current alarm value of slave7"
    ::= { slave7OutputCurrentMax 5}

slave7OutputCurrentMaxSix OBJECT-TYPE
    SYNTAX      DisplayString
    MAX-ACCESS  read-write
    STATUS      current
    DESCRIPTION
	"The second output Max. current alarm value of slave7"
    ::= { slave7OutputCurrentMax 6}

slave7OutputCurrentMaxSeven OBJECT-TYPE
    SYNTAX      DisplayString
    MAX-ACCESS  read-write
    STATUS      current
    DESCRIPTION
	"The second output Max. current alarm value of slave7"
    ::= { slave7OutputCurrentMax 7}

slave7OutputCurrentMaxEight OBJECT-TYPE
    SYNTAX      DisplayString
    MAX-ACCESS  read-write
    STATUS      current
    DESCRIPTION
	"The second output Max. current alarm value of slave7"
    ::= { slave7OutputCurrentMax 8}

slave7OutputCurrentMaxNine OBJECT-TYPE
    SYNTAX      DisplayString
    MAX-ACCESS  read-write
    STATUS      current
    DESCRIPTION
	"The second output Max. current alarm value of slave7"
    ::= { slave7OutputCurrentMax 9}

slave7OutputCurrentMaxTen OBJECT-TYPE
    SYNTAX      DisplayString
    MAX-ACCESS  read-write
    STATUS      current
    DESCRIPTION
	"The second output Max. current alarm value of slave7"
    ::= { slave7OutputCurrentMax 10}

slave7OutputCurrentMaxEleven OBJECT-TYPE
    SYNTAX      DisplayString
    MAX-ACCESS  read-write
    STATUS      current
    DESCRIPTION
	"The second output Max. current alarm value of slave7"
    ::= { slave7OutputCurrentMax 11}

slave7OutputCurrentMaxTwel OBJECT-TYPE
    SYNTAX      DisplayString
    MAX-ACCESS  read-write
    STATUS      current
    DESCRIPTION
	"The second output Max. current alarm value of slave7"
    ::= { slave7OutputCurrentMax 12}

slave7OutputCurrentMaxThirteen OBJECT-TYPE
    SYNTAX      DisplayString
    MAX-ACCESS  read-write
    STATUS      current
    DESCRIPTION
	"The second output Max. current alarm value of slave7"
    ::= { slave7OutputCurrentMax 13}

slave7OutputCurrentMaxFourteen OBJECT-TYPE
    SYNTAX      DisplayString
    MAX-ACCESS  read-write
    STATUS      current
    DESCRIPTION
	"The second output Max. current alarm value of slave7"
    ::= { slave7OutputCurrentMax 14}

slave7OutputCurrentMaxFifteen OBJECT-TYPE
    SYNTAX      DisplayString
    MAX-ACCESS  read-write
    STATUS      current
    DESCRIPTION
	"The second output Max. current alarm value of slave7"
    ::= { slave7OutputCurrentMax 15}

slave7OutputCurrentMaxSixteen OBJECT-TYPE
    SYNTAX      DisplayString
    MAX-ACCESS  read-write
    STATUS      current
    DESCRIPTION
	"The second output Max. current alarm value of slave7"
    ::= { slave7OutputCurrentMax 16}

slave7OutputCurrentMaxSeventeen OBJECT-TYPE
    SYNTAX      DisplayString
    MAX-ACCESS  read-write
    STATUS      current
    DESCRIPTION
	"The second output Max. current alarm value of slave7"
    ::= { slave7OutputCurrentMax 17}

slave7OutputCurrentMaxEighteen OBJECT-TYPE
    SYNTAX      DisplayString
    MAX-ACCESS  read-write
    STATUS      current
    DESCRIPTION
	"The second output Max. current alarm value of slave7"
    ::= { slave7OutputCurrentMax 18}
	
slave7OutputCurrentMaxNineteen OBJECT-TYPE
    SYNTAX      DisplayString
    MAX-ACCESS  read-write
    STATUS      current
    DESCRIPTION
	"The second output Max. current alarm value of slave7"
    ::= { slave7OutputCurrentMax 19}
	
slave7OutputCurrentMaxtwenty OBJECT-TYPE
    SYNTAX      DisplayString
    MAX-ACCESS  read-write
    STATUS      current
    DESCRIPTION
	"The second output Max. current alarm value of slave7"
    ::= { slave7OutputCurrentMax 20}
	
slave7OutputCurrentMaxTwentyone OBJECT-TYPE
    SYNTAX      DisplayString
    MAX-ACCESS  read-write
    STATUS      current
    DESCRIPTION
	"The second output Max. current alarm value of slave7"
    ::= { slave7OutputCurrentMax 21}
	
slave7OutputCurrentMaxTwentyonetwo OBJECT-TYPE
    SYNTAX      DisplayString
    MAX-ACCESS  read-write
    STATUS      current
    DESCRIPTION
	"The second output Max. current alarm value of slave7"
    ::= { slave7OutputCurrentMax 22}
	
slave7OutputCurrentMaxTwentythree OBJECT-TYPE
    SYNTAX      DisplayString
    MAX-ACCESS  read-write
    STATUS      current
    DESCRIPTION
	"The second output Max. current alarm value of slave7"
    ::= { slave7OutputCurrentMax 23}
	
slave7OutputCurrentMaxTwentyfour OBJECT-TYPE
    SYNTAX      DisplayString
    MAX-ACCESS  read-write
    STATUS      current
    DESCRIPTION
	"The second output Max. current alarm value of slave7"
    ::= { slave7OutputCurrentMax 24}
	
slave7OutputCurrentMaxTwentyfive OBJECT-TYPE
    SYNTAX      DisplayString
    MAX-ACCESS  read-write
    STATUS      current
    DESCRIPTION
	"The second output Max. current alarm value of slave7"
    ::= { slave7OutputCurrentMax 25}
	
slave7OutputCurrentMaxTwentysix OBJECT-TYPE
    SYNTAX      DisplayString
    MAX-ACCESS  read-write
    STATUS      current
    DESCRIPTION
	"The second output Max. current alarm value of slave7"
    ::= { slave7OutputCurrentMax 26}
	
slave7OutputCurrentMaxTwentyseven OBJECT-TYPE
    SYNTAX      DisplayString
    MAX-ACCESS  read-write
    STATUS      current
    DESCRIPTION
	"The second output Max. current alarm value of slave7"
    ::= { slave7OutputCurrentMax 27}
	
slave7OutputCurrentMaxTwentyeight OBJECT-TYPE
    SYNTAX      DisplayString
    MAX-ACCESS  read-write
    STATUS      current
    DESCRIPTION
	"The second output Max. current alarm value of slave7"
    ::= { slave7OutputCurrentMax 28}	
slave7OutputCurrentMaxTwentynine OBJECT-TYPE
    SYNTAX      DisplayString
    MAX-ACCESS  read-write
    STATUS      current
    DESCRIPTION
	"The second output Max. current alarm value of slave7"
    ::= { slave7OutputCurrentMax 29}
	
slave7OutputCurrentMaxThirty OBJECT-TYPE
    SYNTAX      DisplayString
    MAX-ACCESS  read-write
    STATUS      current
    DESCRIPTION
	"The second output Max. current alarm value of slave7"
    ::= { slave7OutputCurrentMax 30}
	
slave7OutputCurrentMaxThirtyone OBJECT-TYPE
    SYNTAX      DisplayString
    MAX-ACCESS  read-write
    STATUS      current
    DESCRIPTION
	"The second output Max. current alarm value of slave7"
    ::= { slave7OutputCurrentMax 31}
	
slave7OutputCurrentMaxThirtytwo OBJECT-TYPE
    SYNTAX      DisplayString
    MAX-ACCESS  read-write
    STATUS      current
    DESCRIPTION
	"The second output Max. current alarm value of slave7"
    ::= { slave7OutputCurrentMax 32}
	
slave7OutputCurrentMaxThirtythree OBJECT-TYPE
    SYNTAX      DisplayString
    MAX-ACCESS  read-write
    STATUS      current
    DESCRIPTION
	"The second output Max. current alarm value of slave7"
    ::= { slave7OutputCurrentMax 33}
	
slave7OutputCurrentMaxThirtyfour OBJECT-TYPE
    SYNTAX      DisplayString
    MAX-ACCESS  read-write
    STATUS      current
    DESCRIPTION
	"The second output Max. current alarm value of slave7"
    ::= { slave7OutputCurrentMax 34}
	
slave7OutputCurrentMaxThirtyfive OBJECT-TYPE
    SYNTAX      DisplayString
    MAX-ACCESS  read-write
    STATUS      current
    DESCRIPTION
	"The second output Max. current alarm value of slave7"
    ::= { slave7OutputCurrentMax 35}
	
slave7OutputCurrentMaxThirtysix OBJECT-TYPE
    SYNTAX      DisplayString
    MAX-ACCESS  read-write
    STATUS      current
    DESCRIPTION
	"The second output Max. current alarm value of slave7"
    ::= { slave7OutputCurrentMax 36}
	
slave7OutputCurrentMaxThirtyseven OBJECT-TYPE
    SYNTAX      DisplayString
    MAX-ACCESS  read-write
    STATUS      current
    DESCRIPTION
	"The second output Max. current alarm value of slave7"
    ::= { slave7OutputCurrentMax 37}
	
slave7OutputCurrentMaxThirtyeight OBJECT-TYPE
    SYNTAX      DisplayString
    MAX-ACCESS  read-write
    STATUS      current
    DESCRIPTION
	"The second output Max. current alarm value of slave7"
    ::= { slave7OutputCurrentMax 38}
	
slave7OutputCurrentMaxThirtynine OBJECT-TYPE
    SYNTAX      DisplayString
    MAX-ACCESS  read-write
    STATUS      current
    DESCRIPTION
	"The second output Max. current alarm value of slave7"
    ::= { slave7OutputCurrentMax 39}
	
slave7OutputCurrentMaxFourty OBJECT-TYPE
    SYNTAX      DisplayString
    MAX-ACCESS  read-write
    STATUS      current
    DESCRIPTION
	"The second output Max. current alarm value of slave7"
    ::= { slave7OutputCurrentMax 40}
	
slave7OutputCurrentMaxFourtyone OBJECT-TYPE
    SYNTAX      DisplayString
    MAX-ACCESS  read-write
    STATUS      current
    DESCRIPTION
	"The second output Max. current alarm value of slave7"
    ::= { slave7OutputCurrentMax 41}
	
slave7OutputCurrentMaxFourtytwo OBJECT-TYPE
    SYNTAX      DisplayString
    MAX-ACCESS  read-write
    STATUS      current
    DESCRIPTION
	"The second output Max. current alarm value of slave7"
    ::= { slave7OutputCurrentMax 42}
	
	
-------------------------------slave7 output powerfactor------------------------	
slave7OutputPowerfactor OBJECT IDENTIFIER ::= { slave7 9}	

slave7OutputPowerfactorOne OBJECT-TYPE
    SYNTAX      DisplayString
    MAX-ACCESS  read-only
    STATUS      current
    DESCRIPTION
	"The ouput power factor of slave7." 
	::= { slave7OutputPowerfactor 1}

slave7OutputPowerfactorTwo OBJECT-TYPE
    SYNTAX      DisplayString
    MAX-ACCESS  read-only
    STATUS      current
    DESCRIPTION
	"The ouput power factor of slave7." 
	::= { slave7OutputPowerfactor 2}
	
slave7OutputPowerfactorThree OBJECT-TYPE
    SYNTAX      DisplayString
    MAX-ACCESS  read-only
    STATUS      current
    DESCRIPTION
	"The ouput power factor of slave7." 
	::= { slave7OutputPowerfactor 3}
	
slave7OutputPowerfactorFour OBJECT-TYPE
    SYNTAX      DisplayString
    MAX-ACCESS  read-only
    STATUS      current
    DESCRIPTION
	"The ouput power factor of slave7." 
	::= { slave7OutputPowerfactor 4}
		
slave7OutputPowerfactorFive OBJECT-TYPE
    SYNTAX      DisplayString
    MAX-ACCESS  read-only
    STATUS      current
    DESCRIPTION
	"The ouput power factor of slave7." 
	::= { slave7OutputPowerfactor 5}
	
slave7OutputPowerfactorSix OBJECT-TYPE
    SYNTAX      DisplayString
    MAX-ACCESS  read-only
    STATUS      current
    DESCRIPTION
	"The ouput power factor of slave7." 
	::= { slave7OutputPowerfactor 6}
	
slave7OutputPowerfactorSeven OBJECT-TYPE
    SYNTAX      DisplayString
    MAX-ACCESS  read-only
    STATUS      current
    DESCRIPTION
	"The ouput power factor of slave7." 
	::= { slave7OutputPowerfactor 7}	
	
slave7OutputPowerfactorEight OBJECT-TYPE
    SYNTAX      DisplayString
    MAX-ACCESS  read-only
    STATUS      current
    DESCRIPTION
	"The ouput power factor of slave7." 
	::= { slave7OutputPowerfactor 8}
	
slave7OutputPowerfactorNine OBJECT-TYPE
    SYNTAX      DisplayString
    MAX-ACCESS  read-only
    STATUS      current
    DESCRIPTION
	"The ouput power factor of slave7." 
	::= { slave7OutputPowerfactor 9}
		
slave7OutputPowerfactorTen OBJECT-TYPE
    SYNTAX      DisplayString
    MAX-ACCESS  read-only
    STATUS      current
    DESCRIPTION
	"The ouput power factor of slave7." 
	::= { slave7OutputPowerfactor 10}
		
slave7OutputPowerfactorEleven OBJECT-TYPE
    SYNTAX      DisplayString
    MAX-ACCESS  read-only
    STATUS      current
    DESCRIPTION
	"The ouput power factor of slave7." 
	::= { slave7OutputPowerfactor 11}
		
slave7OutputPowerfactorTwel OBJECT-TYPE
    SYNTAX      DisplayString
    MAX-ACCESS  read-only
    STATUS      current
    DESCRIPTION
	"The ouput power factor of slave7." 
	::= { slave7OutputPowerfactor 12}
		
slave7OutputPowerfactorThirteen OBJECT-TYPE
    SYNTAX      DisplayString
    MAX-ACCESS  read-only
    STATUS      current
    DESCRIPTION
	"The ouput power factor of slave7." 
	::= { slave7OutputPowerfactor 13}
		
slave7OutputPowerfactorFourteen OBJECT-TYPE
    SYNTAX      DisplayString
    MAX-ACCESS  read-only
    STATUS      current
    DESCRIPTION
	"The ouput power factor of slave7." 
	::= { slave7OutputPowerfactor 14}
		
slave7OutputPowerfactorFifteen OBJECT-TYPE
    SYNTAX      DisplayString
    MAX-ACCESS  read-only
    STATUS      current
    DESCRIPTION
	"The ouput power factor of slave7." 
	::= { slave7OutputPowerfactor 15}
		
slave7OutputPowerfactorSixteen OBJECT-TYPE
    SYNTAX      DisplayString
    MAX-ACCESS  read-only
    STATUS      current
    DESCRIPTION
	"The ouput power factor of slave7." 
	::= { slave7OutputPowerfactor 16}
		
slave7OutputPowerfactorSeventeen OBJECT-TYPE
    SYNTAX      DisplayString
    MAX-ACCESS  read-only
    STATUS      current
    DESCRIPTION
	"The ouput power factor of slave7." 
	::= { slave7OutputPowerfactor 17}
		
slave7OutputPowerfactorEighteen OBJECT-TYPE
    SYNTAX      DisplayString
    MAX-ACCESS  read-only
    STATUS      current
    DESCRIPTION
	"The ouput power factor of slave7." 
	::= { slave7OutputPowerfactor 18}
		
slave7OutputPowerfactorNineteen OBJECT-TYPE
    SYNTAX      DisplayString
    MAX-ACCESS  read-only
    STATUS      current
    DESCRIPTION
	"The ouput power factor of slave7." 
	::= { slave7OutputPowerfactor 19}
		
slave7OutputPowerfactorTwenty OBJECT-TYPE
    SYNTAX      DisplayString
    MAX-ACCESS  read-only
    STATUS      current
    DESCRIPTION
	"The ouput power factor of slave7." 
	::= { slave7OutputPowerfactor 20}
		
slave7OutputPowerfactorTwentyone OBJECT-TYPE
    SYNTAX      DisplayString
    MAX-ACCESS  read-only
    STATUS      current
    DESCRIPTION
	"The ouput power factor of slave7." 
	::= { slave7OutputPowerfactor 21}
		
slave7OutputPowerfactorTwentytwo OBJECT-TYPE
    SYNTAX      DisplayString
    MAX-ACCESS  read-only
    STATUS      current
    DESCRIPTION
	"The ouput power factor of slave7." 
	::= { slave7OutputPowerfactor 22}
		
slave7OutputPowerfactorTwentythree OBJECT-TYPE
    SYNTAX      DisplayString
    MAX-ACCESS  read-only
    STATUS      current
    DESCRIPTION
	"The ouput power factor of slave7." 
	::= { slave7OutputPowerfactor 23}
		
slave7OutputPowerfactorTwentyfour OBJECT-TYPE
    SYNTAX      DisplayString
    MAX-ACCESS  read-only
    STATUS      current
    DESCRIPTION
	"The ouput power factor of slave7." 
	::= { slave7OutputPowerfactor 24}
		
slave7OutputPowerfactorTwentyfive OBJECT-TYPE
    SYNTAX      DisplayString
    MAX-ACCESS  read-only
    STATUS      current
    DESCRIPTION
	"The ouput power factor of slave7." 
	::= { slave7OutputPowerfactor 25}
		
slave7OutputPowerfactorTwentysix OBJECT-TYPE
    SYNTAX      DisplayString
    MAX-ACCESS  read-only
    STATUS      current
    DESCRIPTION
	"The ouput power factor of slave7." 
	::= { slave7OutputPowerfactor 26}
		
slave7OutputPowerfactorTwentyseven OBJECT-TYPE
    SYNTAX      DisplayString
    MAX-ACCESS  read-only
    STATUS      current
    DESCRIPTION
	"The ouput power factor of slave7." 
	::= { slave7OutputPowerfactor 27}
		
slave7OutputPowerfactorTwentyeight OBJECT-TYPE
    SYNTAX      DisplayString
    MAX-ACCESS  read-only
    STATUS      current
    DESCRIPTION
	"The ouput power factor of slave7." 
	::= { slave7OutputPowerfactor 28}
		
slave7OutputPowerfactorTwentynine OBJECT-TYPE
    SYNTAX      DisplayString
    MAX-ACCESS  read-only
    STATUS      current
    DESCRIPTION
	"The ouput power factor of slave7." 
	::= { slave7OutputPowerfactor 29}
		
slave7OutputPowerfactorThirty OBJECT-TYPE
    SYNTAX      DisplayString
    MAX-ACCESS  read-only
    STATUS      current
    DESCRIPTION
	"The ouput power factor of slave7." 
	::= { slave7OutputPowerfactor 30}
		
slave7OutputPowerfactorThirtyone OBJECT-TYPE
    SYNTAX      DisplayString
    MAX-ACCESS  read-only
    STATUS      current
    DESCRIPTION
	"The ouput power factor of slave7." 
	::= { slave7OutputPowerfactor 31}
		
slave7OutputPowerfactorThirtytwo OBJECT-TYPE
    SYNTAX      DisplayString
    MAX-ACCESS  read-only
    STATUS      current
    DESCRIPTION
	"The ouput power factor of slave7." 
	::= { slave7OutputPowerfactor 32}
		
slave7OutputPowerfactorThirtythree OBJECT-TYPE
    SYNTAX      DisplayString
    MAX-ACCESS  read-only
    STATUS      current
    DESCRIPTION
	"The ouput power factor of slave7." 
	::= { slave7OutputPowerfactor 33}	
	
slave7OutputPowerfactorThirtyfour OBJECT-TYPE
    SYNTAX      DisplayString
    MAX-ACCESS  read-only
    STATUS      current
    DESCRIPTION
	"The ouput power factor of slave7." 
	::= { slave7OutputPowerfactor 34}
	
	
slave7OutputPowerfactorThirtyfive OBJECT-TYPE
    SYNTAX      DisplayString
    MAX-ACCESS  read-only
    STATUS      current
    DESCRIPTION
	"The ouput power factor of slave7." 
	::= { slave7OutputPowerfactor 35}
		
slave7OutputPowerfactorThirtysix OBJECT-TYPE
    SYNTAX      DisplayString
    MAX-ACCESS  read-only
    STATUS      current
    DESCRIPTION
	"The ouput power factor of slave7." 
	::= { slave7OutputPowerfactor 36}
		
slave7OutputPowerfactorThirtyseven OBJECT-TYPE
    SYNTAX      DisplayString
    MAX-ACCESS  read-only
    STATUS      current
    DESCRIPTION
	"The ouput power factor of slave7." 
	::= { slave7OutputPowerfactor 37}
		
slave7OutputPowerfactorThirtyeight OBJECT-TYPE
    SYNTAX      DisplayString
    MAX-ACCESS  read-only
    STATUS      current
    DESCRIPTION
	"The ouput power factor of slave7." 
	::= { slave7OutputPowerfactor 38}
		
slave7OutputPowerfactorThirtynine OBJECT-TYPE
    SYNTAX      DisplayString
    MAX-ACCESS  read-only
    STATUS      current
    DESCRIPTION
	"The ouput power factor of slave7." 
	::= { slave7OutputPowerfactor 39}
		
slave7OutputPowerfactorFourty OBJECT-TYPE
    SYNTAX      DisplayString
    MAX-ACCESS  read-only
    STATUS      current
    DESCRIPTION
	"The ouput power factor of slave7." 
	::= { slave7OutputPowerfactor 40}
		
slave7OutputPowerfactorFourtyone OBJECT-TYPE
    SYNTAX      DisplayString
    MAX-ACCESS  read-only
    STATUS      current
    DESCRIPTION
	"The ouput power factor of slave7." 
	::= { slave7OutputPowerfactor 41}
		
slave7OutputPowerfactorFourtytwo OBJECT-TYPE
    SYNTAX      DisplayString
    MAX-ACCESS  read-only
    STATUS      current
    DESCRIPTION
	"The ouput power factor of slave7." 
	::= { slave7OutputPowerfactor 42}	
	
-------------------------------slave7 output energy------------------------	
slave7OutputEnergy OBJECT IDENTIFIER ::= { slave7 10}

slave7OutputEnergyOne OBJECT-TYPE
    SYNTAX      DisplayString
    MAX-ACCESS  read-only
    STATUS      current
    DESCRIPTION
	"The ouput power of slave7." 
	::= { slave7OutputEnergy 1}

slave7OutputEnergyTwo OBJECT-TYPE
    SYNTAX      DisplayString
    MAX-ACCESS  read-only
    STATUS      current
    DESCRIPTION
	"The ouput power of slave7." 
	::= { slave7OutputEnergy 2}
	
slave7OutputEnergyThree OBJECT-TYPE
    SYNTAX      DisplayString
    MAX-ACCESS  read-only
    STATUS      current
    DESCRIPTION
	"The ouput power of slave7." 
	::= { slave7OutputEnergy 3}
	
slave7OutputEnergyFour OBJECT-TYPE
    SYNTAX      DisplayString
    MAX-ACCESS  read-only
    STATUS      current
    DESCRIPTION
	"The ouput power of slave7." 
	::= { slave7OutputEnergy 4}
		
slave7OutputEnergyFive OBJECT-TYPE
    SYNTAX      DisplayString
    MAX-ACCESS  read-only
    STATUS      current
    DESCRIPTION
	"The ouput power of slave7." 
	::= { slave7OutputEnergy 5}
	
slave7OutputEnergySix OBJECT-TYPE
    SYNTAX      DisplayString
    MAX-ACCESS  read-only
    STATUS      current
    DESCRIPTION
	"The ouput power of slave7." 
	::= { slave7OutputEnergy 6}
	
slave7OutputEnergySeven OBJECT-TYPE
    SYNTAX      DisplayString
    MAX-ACCESS  read-only
    STATUS      current
    DESCRIPTION
	"The ouput power of slave7." 
	::= { slave7OutputEnergy 7}	
	
slave7OutputEnergyEight OBJECT-TYPE
    SYNTAX      DisplayString
    MAX-ACCESS  read-only
    STATUS      current
    DESCRIPTION
	"The ouput power of slave7." 
	::= { slave7OutputEnergy 8}
	
slave7OutputEnergyNine OBJECT-TYPE
    SYNTAX      DisplayString
    MAX-ACCESS  read-only
    STATUS      current
    DESCRIPTION
	"The ouput power of slave7." 
	::= { slave7OutputEnergy 9}
		
slave7OutputEnergyTen OBJECT-TYPE
    SYNTAX      DisplayString
    MAX-ACCESS  read-only
    STATUS      current
    DESCRIPTION
	"The ouput power of slave7." 
	::= { slave7OutputEnergy 10}
		
slave7OutputEnergyEleven OBJECT-TYPE
    SYNTAX      DisplayString
    MAX-ACCESS  read-only
    STATUS      current
    DESCRIPTION
	"The ouput power of slave7." 
	::= { slave7OutputEnergy 11}
		
slave7OutputEnergyTwel OBJECT-TYPE
    SYNTAX      DisplayString
    MAX-ACCESS  read-only
    STATUS      current
    DESCRIPTION
	"The ouput power of slave7." 
	::= { slave7OutputEnergy 12}
		
slave7OutputEnergyThirteen OBJECT-TYPE
    SYNTAX      DisplayString
    MAX-ACCESS  read-only
    STATUS      current
    DESCRIPTION
	"The ouput power of slave7." 
	::= { slave7OutputEnergy 13}
		
slave7OutputEnergyFourteen OBJECT-TYPE
    SYNTAX      DisplayString
    MAX-ACCESS  read-only
    STATUS      current
    DESCRIPTION
	"The ouput power of slave7." 
	::= { slave7OutputEnergy 14}
		
slave7OutputEnergyFifteen OBJECT-TYPE
    SYNTAX      DisplayString
    MAX-ACCESS  read-only
    STATUS      current
    DESCRIPTION
	"The ouput power of slave7." 
	::= { slave7OutputEnergy 15}
		
slave7OutputEnergySixteen OBJECT-TYPE
    SYNTAX      DisplayString
    MAX-ACCESS  read-only
    STATUS      current
    DESCRIPTION
	"The ouput power of slave7." 
	::= { slave7OutputEnergy 16}
		
slave7OutputEnergySeventeen OBJECT-TYPE
    SYNTAX      DisplayString
    MAX-ACCESS  read-only
    STATUS      current
    DESCRIPTION
	"The ouput power of slave7." 
	::= { slave7OutputEnergy 17}
		
slave7OutputEnergyEighteen OBJECT-TYPE
    SYNTAX      DisplayString
    MAX-ACCESS  read-only
    STATUS      current
    DESCRIPTION
	"The ouput power of slave7." 
	::= { slave7OutputEnergy 18}
		
slave7OutputEnergyNineteen OBJECT-TYPE
    SYNTAX      DisplayString
    MAX-ACCESS  read-only
    STATUS      current
    DESCRIPTION
	"The ouput power of slave7." 
	::= { slave7OutputEnergy 19}
		
slave7OutputEnergyTwenty OBJECT-TYPE
    SYNTAX      DisplayString
    MAX-ACCESS  read-only
    STATUS      current
    DESCRIPTION
	"The ouput power of slave7." 
	::= { slave7OutputEnergy 20}
		
slave7OutputEnergyTwentyone OBJECT-TYPE
    SYNTAX      DisplayString
    MAX-ACCESS  read-only
    STATUS      current
    DESCRIPTION
	"The ouput power of slave7." 
	::= { slave7OutputEnergy 21}
		
slave7OutputEnergyTwentytwo OBJECT-TYPE
    SYNTAX      DisplayString
    MAX-ACCESS  read-only
    STATUS      current
    DESCRIPTION
	"The ouput power of slave7." 
	::= { slave7OutputEnergy 22}
		
slave7OutputEnergyTwentythree OBJECT-TYPE
    SYNTAX      DisplayString
    MAX-ACCESS  read-only
    STATUS      current
    DESCRIPTION
	"The ouput power of slave7." 
	::= { slave7OutputEnergy 23}
		
slave7OutputEnergyTwentyfour OBJECT-TYPE
    SYNTAX      DisplayString
    MAX-ACCESS  read-only
    STATUS      current
    DESCRIPTION
	"The ouput power of slave7." 
	::= { slave7OutputEnergy 24}
		
slave7OutputEnergyTwentyfive OBJECT-TYPE
    SYNTAX      DisplayString
    MAX-ACCESS  read-only
    STATUS      current
    DESCRIPTION
	"The ouput power of slave7." 
	::= { slave7OutputEnergy 25}
		
slave7OutputEnergyTwentysix OBJECT-TYPE
    SYNTAX      DisplayString
    MAX-ACCESS  read-only
    STATUS      current
    DESCRIPTION
	"The ouput power of slave7." 
	::= { slave7OutputEnergy 26}
		
slave7OutputEnergyTwentyseven OBJECT-TYPE
    SYNTAX      DisplayString
    MAX-ACCESS  read-only
    STATUS      current
    DESCRIPTION
	"The ouput power of slave7." 
	::= { slave7OutputEnergy 27}
		
slave7OutputEnergyTwentyeight OBJECT-TYPE
    SYNTAX      DisplayString
    MAX-ACCESS  read-only
    STATUS      current
    DESCRIPTION
	"The ouput power of slave7." 
	::= { slave7OutputEnergy 28}
		
slave7OutputEnergyTwentynine OBJECT-TYPE
    SYNTAX      DisplayString
    MAX-ACCESS  read-only
    STATUS      current
    DESCRIPTION
	"The ouput power of slave7." 
	::= { slave7OutputEnergy 29}
		
slave7OutputEnergyThirty OBJECT-TYPE
    SYNTAX      DisplayString
    MAX-ACCESS  read-only
    STATUS      current
    DESCRIPTION
	"The ouput power of slave7." 
	::= { slave7OutputEnergy 30}
		
slave7OutputEnergyThirtyone OBJECT-TYPE
    SYNTAX      DisplayString
    MAX-ACCESS  read-only
    STATUS      current
    DESCRIPTION
	"The ouput power of slave7." 
	::= { slave7OutputEnergy 31}
		
slave7OutputEnergyThirtytwo OBJECT-TYPE
    SYNTAX      DisplayString
    MAX-ACCESS  read-only
    STATUS      current
    DESCRIPTION
	"The ouput power of slave7." 
	::= { slave7OutputEnergy 32}
		
slave7OutputEnergyThirtythree OBJECT-TYPE
    SYNTAX      DisplayString
    MAX-ACCESS  read-only
    STATUS      current
    DESCRIPTION
	"The ouput power of slave7." 
	::= { slave7OutputEnergy 33}	
	
slave7OutputEnergyThirtyfour OBJECT-TYPE
    SYNTAX      DisplayString
    MAX-ACCESS  read-only
    STATUS      current
    DESCRIPTION
	"The ouput power of slave7." 
	::= { slave7OutputEnergy 34}
	
	
slave7OutputEnergyThirtyfive OBJECT-TYPE
    SYNTAX      DisplayString
    MAX-ACCESS  read-only
    STATUS      current
    DESCRIPTION
	"The ouput power of slave7." 
	::= { slave7OutputEnergy 35}
		
slave7OutputEnergyThirtysix OBJECT-TYPE
    SYNTAX      DisplayString
    MAX-ACCESS  read-only
    STATUS      current
    DESCRIPTION
	"The ouput power of slave7." 
	::= { slave7OutputEnergy 36}
		
slave7OutputEnergyThirtyseven OBJECT-TYPE
    SYNTAX      DisplayString
    MAX-ACCESS  read-only
    STATUS      current
    DESCRIPTION
	"The ouput power of slave7." 
	::= { slave7OutputEnergy 37}
		
slave7OutputEnergyThirtyeight OBJECT-TYPE
    SYNTAX      DisplayString
    MAX-ACCESS  read-only
    STATUS      current
    DESCRIPTION
	"The ouput power of slave7." 
	::= { slave7OutputEnergy 38}
		
slave7OutputEnergyThirtynine OBJECT-TYPE
    SYNTAX      DisplayString
    MAX-ACCESS  read-only
    STATUS      current
    DESCRIPTION
	"The ouput power of slave7." 
	::= { slave7OutputEnergy 39}
		
slave7OutputEnergyFourty OBJECT-TYPE
    SYNTAX      DisplayString
    MAX-ACCESS  read-only
    STATUS      current
    DESCRIPTION
	"The ouput power of slave7." 
	::= { slave7OutputEnergy 40}
		
slave7OutputEnergyFourtyone OBJECT-TYPE
    SYNTAX      DisplayString
    MAX-ACCESS  read-only
    STATUS      current
    DESCRIPTION
	"The ouput power of slave7." 
	::= { slave7OutputEnergy 41}
		
slave7OutputEnergyFourtytwo OBJECT-TYPE
    SYNTAX      DisplayString
    MAX-ACCESS  read-only
    STATUS      current
    DESCRIPTION
	"The ouput power of slave7." 
	::= { slave7OutputEnergy 42}	


	



-------------------------------slave8 information--------------------
slave8 OBJECT IDENTIFIER ::= { pdu 9}
slave8Information OBJECT IDENTIFIER ::= { slave8 1}
slave8Name OBJECT-TYPE
    SYNTAX      DisplayString
    MAX-ACCESS  read-write
    STATUS      current
    DESCRIPTION
	"This is the first device."
    ::= { slave8Information 1}
    
slave8Type OBJECT-TYPE
    SYNTAX      DisplayString
    MAX-ACCESS  read-only
    STATUS      current
    DESCRIPTION
	"This is device type "
    ::= { slave8Information 2}
    
slave8OutputNumber OBJECT-TYPE 
    SYNTAX      Integer32
    MAX-ACCESS  read-only
    STATUS      current
    DESCRIPTION
	"This is the number of output bits"
	::= { slave8Information 3}
	
slave8MacAdress OBJECT-TYPE
    SYNTAX      DisplayString
    MAX-ACCESS  read-only
    STATUS      current
    DESCRIPTION
	"This is device MAC adress"
    ::= { slave8Information 4}	

slave8Vison OBJECT-TYPE
    SYNTAX      DisplayString
    MAX-ACCESS  read-only
    STATUS      current
    DESCRIPTION
	"This is device vison "
    ::= { slave8Information 5}

slave8Frequency OBJECT-TYPE
    SYNTAX      Integer32
    MAX-ACCESS  read-only
    STATUS      current
    DESCRIPTION
	"This is device frequency "
    ::= { slave8Information 6}
	
slave8Emission OBJECT-TYPE
    SYNTAX      DisplayString
    MAX-ACCESS  read-only
    STATUS      current
    DESCRIPTION
	"This is device emission "
    ::= { slave8Information 7}	
	
slave8RunTime OBJECT-TYPE
    SYNTAX      DisplayString
    MAX-ACCESS  read-only
    STATUS      current
    DESCRIPTION
	"This is device running time "
    ::= { slave8Information 8}	

slave8BuzzerSwitch OBJECT-TYPE
    SYNTAX      DisplayString
    MAX-ACCESS  read-write
    STATUS      current
    DESCRIPTION
	"This is device buzzer switch."
    ::= { slave8Information 9}	

	
-------------------------------slave8 phase--------------------
slave8Phase OBJECT IDENTIFIER ::= { slave8 2}	
	
slave8PhaseOne OBJECT IDENTIFIER ::= { slave8Phase 1}	    
slave8PhaseOneCurrent OBJECT-TYPE
    SYNTAX      DisplayString
    MAX-ACCESS  read-only
    STATUS      current
    DESCRIPTION
	"The power of phase one"
    ::= { slave8PhaseOne 1}

slave8PhaseOneVoltage OBJECT-TYPE
    SYNTAX      DisplayString
    MAX-ACCESS  read-only
    STATUS      current
    DESCRIPTION
	"The power of phase one"
    ::= { slave8PhaseOne 2}

slave8PhaseOnePower OBJECT-TYPE
    SYNTAX      DisplayString
    MAX-ACCESS  read-only
    STATUS      current
    DESCRIPTION
	"The power of phase one"
    ::= { slave8PhaseOne 3}
	
slave8PhaseOnePowerfactor OBJECT-TYPE
    SYNTAX      DisplayString
    MAX-ACCESS  read-only
    STATUS      current
    DESCRIPTION
	"The power of phase one"
    ::= { slave8PhaseOne 4}	
	
slave8PhaseOneEnergy OBJECT-TYPE
    SYNTAX      DisplayString
    MAX-ACCESS  read-only
    STATUS      current
    DESCRIPTION
	"The power of phase one"
    ::= { slave8PhaseOne 5}	
		
slave8PhaseOneCurrentMin OBJECT-TYPE
    SYNTAX      DisplayString
    MAX-ACCESS  read-write
    STATUS      current
    DESCRIPTION
	"The power of phase one"
    ::= { slave8PhaseOne 6}	
	
slave8PhaseOneCurrentMinCritical OBJECT-TYPE
    SYNTAX      DisplayString
    MAX-ACCESS  read-write
    STATUS      current
    DESCRIPTION
	"The power of phase one"
    ::= { slave8PhaseOne 7}
	
slave8PhaseOneCurrentMaxCritical OBJECT-TYPE
    SYNTAX      DisplayString
    MAX-ACCESS  read-write
    STATUS      current
    DESCRIPTION
	"The power of phase one"
    ::= { slave8PhaseOne 8}
	
slave8PhaseOneCurrentMax OBJECT-TYPE
    SYNTAX      DisplayString
    MAX-ACCESS  read-write
    STATUS      current
    DESCRIPTION
	"The power of phase one"
    ::= { slave8PhaseOne 9}
	
slave8PhaseOneVoltageMin OBJECT-TYPE
    SYNTAX      DisplayString
    MAX-ACCESS  read-write
    STATUS      current
    DESCRIPTION
	"The power of phase one"
    ::= { slave8PhaseOne 10}
	
slave8PhaseOneVoltageMinCritical OBJECT-TYPE
    SYNTAX      DisplayString
    MAX-ACCESS  read-write
    STATUS      current
    DESCRIPTION
	"The power of phase one"
    ::= { slave8PhaseOne 11}

slave8PhaseOneVoltageMaxCritical OBJECT-TYPE
    SYNTAX      DisplayString
    MAX-ACCESS  read-write
    STATUS      current
    DESCRIPTION
	"The power of phase one"
    ::= { slave8PhaseOne 12}
	
slave8PhaseOneVoltageMax OBJECT-TYPE
    SYNTAX      DisplayString
    MAX-ACCESS  read-write
    STATUS      current
    DESCRIPTION
	"The power of phase one"
    ::= { slave8PhaseOne 13}


slave8PhaseTwo OBJECT IDENTIFIER ::= { slave8Phase 2}	    
slave8PhaseTwoCurrent OBJECT-TYPE
    SYNTAX      DisplayString
    MAX-ACCESS  read-only
    STATUS      current
    DESCRIPTION
	"The power of phase one"
    ::= { slave8PhaseTwo 1}

slave8PhaseTwoVoltage OBJECT-TYPE
    SYNTAX      DisplayString
    MAX-ACCESS  read-only
    STATUS      current
    DESCRIPTION
	"The power of phase one"
    ::= { slave8PhaseTwo 2}

slave8PhaseTwoPower OBJECT-TYPE
    SYNTAX      DisplayString
    MAX-ACCESS  read-only
    STATUS      current
    DESCRIPTION
	"The power of phase one"
    ::= { slave8PhaseTwo 3}
	
slave8PhaseTwoPowerfactor OBJECT-TYPE
    SYNTAX      DisplayString
    MAX-ACCESS  read-only
    STATUS      current
    DESCRIPTION
	"The power of phase one"
    ::= { slave8PhaseTwo 4}	
	
slave8PhaseTwoEnergy OBJECT-TYPE
    SYNTAX      DisplayString
    MAX-ACCESS  read-only
    STATUS      current
    DESCRIPTION
	"The power of phase one"
    ::= { slave8PhaseTwo 5}	
		
slave8PhaseTwoCurrentMin OBJECT-TYPE
    SYNTAX      DisplayString
    MAX-ACCESS  read-write
    STATUS      current
    DESCRIPTION
	"The power of phase one"
    ::= { slave8PhaseTwo 6}	
	
slave8PhaseTwoCurrentMinCritical OBJECT-TYPE
    SYNTAX      DisplayString
    MAX-ACCESS  read-write
    STATUS      current
    DESCRIPTION
	"The power of phase one"
    ::= { slave8PhaseTwo 7}
	
slave8PhaseTwoCurrentMaxCritical OBJECT-TYPE
    SYNTAX      DisplayString
    MAX-ACCESS  read-write
    STATUS      current
    DESCRIPTION
	"The power of phase one"
    ::= { slave8PhaseTwo 8}
	
slave8PhaseTwoCurrentMax OBJECT-TYPE
    SYNTAX      DisplayString
    MAX-ACCESS  read-write
    STATUS      current
    DESCRIPTION
	"The power of phase one"
    ::= { slave8PhaseTwo 9}
	
slave8PhaseTwoVoltageMin OBJECT-TYPE
    SYNTAX      DisplayString
    MAX-ACCESS  read-write
    STATUS      current
    DESCRIPTION
	"The power of phase one"
    ::= { slave8PhaseTwo 10}
	
slave8PhaseTwoVoltageMinCritical OBJECT-TYPE
    SYNTAX      DisplayString
    MAX-ACCESS  read-write
    STATUS      current
    DESCRIPTION
	"The power of phase one"
    ::= { slave8PhaseTwo 11}

slave8PhaseTwoVoltageMaxCritical OBJECT-TYPE
    SYNTAX      DisplayString
    MAX-ACCESS  read-write
    STATUS      current
    DESCRIPTION
	"The power of phase one"
    ::= { slave8PhaseTwo 12}
	
slave8PhaseTwoVoltageMax OBJECT-TYPE
    SYNTAX      DisplayString
    MAX-ACCESS  read-write
    STATUS      current
    DESCRIPTION
	"The power of phase one"
    ::= { slave8PhaseTwo 13}
	
	
slave8PhaseThree OBJECT IDENTIFIER ::= { slave8Phase 3}	    
slave8PhaseThreeCurrent OBJECT-TYPE
    SYNTAX      DisplayString
    MAX-ACCESS  read-only
    STATUS      current
    DESCRIPTION
	"The power of phase one"
    ::= { slave8PhaseThree 1}

slave8PhaseThreeVoltage OBJECT-TYPE
    SYNTAX      DisplayString
    MAX-ACCESS  read-only
    STATUS      current
    DESCRIPTION
	"The power of phase one"
    ::= { slave8PhaseThree 2}

slave8PhaseThreePower OBJECT-TYPE
    SYNTAX      DisplayString
    MAX-ACCESS  read-only
    STATUS      current
    DESCRIPTION
	"The power of phase one"
    ::= { slave8PhaseThree 3}
	
slave8PhaseThreePowerfactor OBJECT-TYPE
    SYNTAX      DisplayString
    MAX-ACCESS  read-only
    STATUS      current
    DESCRIPTION
	"The power of phase one"
    ::= { slave8PhaseThree 4}	
	
slave8PhaseThreeEnergy OBJECT-TYPE
    SYNTAX      DisplayString
    MAX-ACCESS  read-only
    STATUS      current
    DESCRIPTION
	"The power of phase one"
    ::= { slave8PhaseThree 5}	
		
slave8PhaseThreeCurrentMin OBJECT-TYPE
    SYNTAX      DisplayString
    MAX-ACCESS  read-write
    STATUS      current
    DESCRIPTION
	"The power of phase one"
    ::= { slave8PhaseThree 6}	
	
slave8PhaseThreeCurrentMinCritical OBJECT-TYPE
    SYNTAX      DisplayString
    MAX-ACCESS  read-write
    STATUS      current
    DESCRIPTION
	"The power of phase one"
    ::= { slave8PhaseThree 7}
	
slave8PhaseThreeCurrentMaxCritical OBJECT-TYPE
    SYNTAX      DisplayString
    MAX-ACCESS  read-write
    STATUS      current
    DESCRIPTION
	"The power of phase one"
    ::= { slave8PhaseThree 8}
	
slave8PhaseThreeCurrentMax OBJECT-TYPE
    SYNTAX      DisplayString
    MAX-ACCESS  read-write
    STATUS      current
    DESCRIPTION
	"The power of phase one"
    ::= { slave8PhaseThree 9}
	
slave8PhaseThreeVoltageMin OBJECT-TYPE
    SYNTAX      DisplayString
    MAX-ACCESS  read-write
    STATUS      current
    DESCRIPTION
	"The power of phase one"
    ::= { slave8PhaseThree 10}
	
slave8PhaseThreeVoltageMinCritical OBJECT-TYPE
    SYNTAX      DisplayString
    MAX-ACCESS  read-write
    STATUS      current
    DESCRIPTION
	"The power of phase one"
    ::= { slave8PhaseThree 11}

slave8PhaseThreeVoltageMaxCritical OBJECT-TYPE
    SYNTAX      DisplayString
    MAX-ACCESS  read-write
    STATUS      current
    DESCRIPTION
	"The power of phase one"
    ::= { slave8PhaseThree 12}
	
slave8PhaseThreeVoltageMax OBJECT-TYPE
    SYNTAX      DisplayString
    MAX-ACCESS  read-write
    STATUS      current
    DESCRIPTION
	"The power of phase one"
    ::= { slave8PhaseThree 13}
	
	
-------------------------------slave8 circuit--------------------	
slave8Circuit OBJECT IDENTIFIER ::= { slave8 3}	

slave8CircuitOne OBJECT IDENTIFIER ::= { slave8Circuit 1}	    
slave8CircuitOneBreaker OBJECT-TYPE
    SYNTAX      DisplayString
    MAX-ACCESS  read-only
    STATUS      current
    DESCRIPTION
	"The power of phase one"
    ::= { slave8CircuitOne 1}
	
slave8CircuitOneManagementBit OBJECT-TYPE
    SYNTAX      DisplayString
    MAX-ACCESS  read-only
    STATUS      current
    DESCRIPTION
	"The power of phase one"
    ::= { slave8CircuitOne 2}	

slave8CircuitOneCurrent OBJECT-TYPE
    SYNTAX      DisplayString
    MAX-ACCESS  read-only
    STATUS      current
    DESCRIPTION
	"The power of phase one"
    ::= { slave8CircuitOne 3}

slave8CircuitOneVoltage OBJECT-TYPE
    SYNTAX      DisplayString
    MAX-ACCESS  read-only
    STATUS      current
    DESCRIPTION
	"The power of phase one"
    ::= { slave8CircuitOne 4}

slave8CircuitOneEnergy OBJECT-TYPE
    SYNTAX      DisplayString
    MAX-ACCESS  read-only
    STATUS      current
    DESCRIPTION
	"The power of phase one"
    ::= { slave8CircuitOne 5}	
	
slave8CircuitOnePower OBJECT-TYPE
    SYNTAX      DisplayString
    MAX-ACCESS  read-only
    STATUS      current
    DESCRIPTION
	"The power of phase one"
    ::= { slave8CircuitOne 6}
	
slave8CircuitOneCurrentMin OBJECT-TYPE
    SYNTAX      DisplayString
    MAX-ACCESS  read-write
    STATUS      current
    DESCRIPTION
	"The power of phase one"
    ::= { slave8CircuitOne 7}	
	
slave8CircuitOneCurrentMinCritical OBJECT-TYPE
    SYNTAX      DisplayString
    MAX-ACCESS  read-write
    STATUS      current
    DESCRIPTION
	"The power of phase one"
    ::= { slave8CircuitOne 8}
	
slave8CircuitOneCurrentMaxCritical OBJECT-TYPE
    SYNTAX      DisplayString
    MAX-ACCESS  read-write
    STATUS      current
    DESCRIPTION
	"The power of phase one"
    ::= { slave8CircuitOne 9}
	
slave8CircuitOneCurrentMax OBJECT-TYPE
    SYNTAX      DisplayString
    MAX-ACCESS  read-write
    STATUS      current
    DESCRIPTION
	"The power of phase one"
    ::= { slave8CircuitOne 10}
	

slave8CircuitTwo OBJECT IDENTIFIER ::= { slave8Circuit 2}	    
slave8CircuitTwoBreaker OBJECT-TYPE
    SYNTAX      DisplayString
    MAX-ACCESS  read-only
    STATUS      current
    DESCRIPTION
	"The power of phase one"
    ::= { slave8CircuitTwo 1}
	
slave8CircuitTwoManagementBit OBJECT-TYPE
    SYNTAX      DisplayString
    MAX-ACCESS  read-only
    STATUS      current
    DESCRIPTION
	"The power of phase one"
    ::= { slave8CircuitTwo 2}	

slave8CircuitTwoCurrent OBJECT-TYPE
    SYNTAX      DisplayString
    MAX-ACCESS  read-only
    STATUS      current
    DESCRIPTION
	"The power of phase one"
    ::= { slave8CircuitTwo 3}

slave8CircuitTwoVoltage OBJECT-TYPE
    SYNTAX      DisplayString
    MAX-ACCESS  read-only
    STATUS      current
    DESCRIPTION
	"The power of phase one"
    ::= { slave8CircuitTwo 4}

slave8CircuitTwoEnergy OBJECT-TYPE
    SYNTAX      DisplayString
    MAX-ACCESS  read-only
    STATUS      current
    DESCRIPTION
	"The power of phase one"
    ::= { slave8CircuitTwo 5}	
	
slave8CircuitTwoPower OBJECT-TYPE
    SYNTAX      DisplayString
    MAX-ACCESS  read-only
    STATUS      current
    DESCRIPTION
	"The power of phase one"
    ::= { slave8CircuitTwo 6}
	
slave8CircuitTwoCurrentMin OBJECT-TYPE
    SYNTAX      DisplayString
    MAX-ACCESS  read-write
    STATUS      current
    DESCRIPTION
	"The power of phase one"
    ::= { slave8CircuitTwo 7}	
	
slave8CircuitTwoCurrentMinCritical OBJECT-TYPE
    SYNTAX      DisplayString
    MAX-ACCESS  read-write
    STATUS      current
    DESCRIPTION
	"The power of phase one"
    ::= { slave8CircuitTwo 8}
	
slave8CircuitTwoCurrentMaxCritical OBJECT-TYPE
    SYNTAX      DisplayString
    MAX-ACCESS  read-write
    STATUS      current
    DESCRIPTION
	"The power of phase one"
    ::= { slave8CircuitTwo 9}
	
slave8CircuitTwoCurrentMax OBJECT-TYPE
    SYNTAX      DisplayString
    MAX-ACCESS  read-write
    STATUS      current
    DESCRIPTION
	"The power of phase one"
    ::= { slave8CircuitTwo 10}
	
	
slave8CircuitThree OBJECT IDENTIFIER ::= { slave8Circuit 3}	    
slave8CircuitThreeBreaker OBJECT-TYPE
    SYNTAX      DisplayString
    MAX-ACCESS  read-only
    STATUS      current
    DESCRIPTION
	"The power of phase one"
    ::= { slave8CircuitThree 1}
	
slave8CircuitThreeManagementBit OBJECT-TYPE
    SYNTAX      DisplayString
    MAX-ACCESS  read-only
    STATUS      current
    DESCRIPTION
	"The power of phase one"
    ::= { slave8CircuitThree 2}	

slave8CircuitThreeCurrent OBJECT-TYPE
    SYNTAX      DisplayString
    MAX-ACCESS  read-only
    STATUS      current
    DESCRIPTION
	"The power of phase one"
    ::= { slave8CircuitThree 3}

slave8CircuitThreeVoltage OBJECT-TYPE
    SYNTAX      DisplayString
    MAX-ACCESS  read-only
    STATUS      current
    DESCRIPTION
	"The power of phase one"
    ::= { slave8CircuitThree 4}

slave8CircuitThreeEnergy OBJECT-TYPE
    SYNTAX      DisplayString
    MAX-ACCESS  read-only
    STATUS      current
    DESCRIPTION
	"The power of phase one"
    ::= { slave8CircuitThree 5}	
	
slave8CircuitThreePower OBJECT-TYPE
    SYNTAX      DisplayString
    MAX-ACCESS  read-only
    STATUS      current
    DESCRIPTION
	"The power of phase one"
    ::= { slave8CircuitThree 6}
	
slave8CircuitThreeCurrentMin OBJECT-TYPE
    SYNTAX      DisplayString
    MAX-ACCESS  read-write
    STATUS      current
    DESCRIPTION
	"The power of phase one"
    ::= { slave8CircuitThree 7}	
	
slave8CircuitThreeCurrentMinCritical OBJECT-TYPE
    SYNTAX      DisplayString
    MAX-ACCESS  read-write
    STATUS      current
    DESCRIPTION
	"The power of phase one"
    ::= { slave8CircuitThree 8}
	
slave8CircuitThreeCurrentMaxCritical OBJECT-TYPE
    SYNTAX      DisplayString
    MAX-ACCESS  read-write
    STATUS      current
    DESCRIPTION
	"The power of phase one"
    ::= { slave8CircuitThree 9}
	
slave8CircuitThreeCurrentMax OBJECT-TYPE
    SYNTAX      DisplayString
    MAX-ACCESS  read-write
    STATUS      current
    DESCRIPTION
	"The power of phase one"
    ::= { slave8CircuitThree 10}
	
	
slave8CircuitFour OBJECT IDENTIFIER ::= { slave8Circuit 4}	    
slave8CircuitFourBreaker OBJECT-TYPE
    SYNTAX      DisplayString
    MAX-ACCESS  read-only
    STATUS      current
    DESCRIPTION
	"The power of phase one"
    ::= { slave8CircuitFour 1}
	
slave8CircuitFourManagementBit OBJECT-TYPE
    SYNTAX      DisplayString
    MAX-ACCESS  read-only
    STATUS      current
    DESCRIPTION
	"The power of phase one"
    ::= { slave8CircuitFour 2}	

slave8CircuitFourCurrent OBJECT-TYPE
    SYNTAX      DisplayString
    MAX-ACCESS  read-only
    STATUS      current
    DESCRIPTION
	"The power of phase one"
    ::= { slave8CircuitFour 3}

slave8CircuitFourVoltage OBJECT-TYPE
    SYNTAX      DisplayString
    MAX-ACCESS  read-only
    STATUS      current
    DESCRIPTION
	"The power of phase one"
    ::= { slave8CircuitFour 4}

slave8CircuitFourEnergy OBJECT-TYPE
    SYNTAX      DisplayString
    MAX-ACCESS  read-only
    STATUS      current
    DESCRIPTION
	"The power of phase one"
    ::= { slave8CircuitFour 5}	
	
slave8CircuitFourPower OBJECT-TYPE
    SYNTAX      DisplayString
    MAX-ACCESS  read-only
    STATUS      current
    DESCRIPTION
	"The power of phase one"
    ::= { slave8CircuitFour 6}
	
slave8CircuitFourCurrentMin OBJECT-TYPE
    SYNTAX      DisplayString
    MAX-ACCESS  read-write
    STATUS      current
    DESCRIPTION
	"The power of phase one"
    ::= { slave8CircuitFour 7}	
	
slave8CircuitFourCurrentMinCritical OBJECT-TYPE
    SYNTAX      DisplayString
    MAX-ACCESS  read-write
    STATUS      current
    DESCRIPTION
	"The power of phase one"
    ::= { slave8CircuitFour 8}
	
slave8CircuitFourCurrentMaxCritical OBJECT-TYPE
    SYNTAX      DisplayString
    MAX-ACCESS  read-write
    STATUS      current
    DESCRIPTION
	"The power of phase one"
    ::= { slave8CircuitFour 9}
	
slave8CircuitFourCurrentMax OBJECT-TYPE
    SYNTAX      DisplayString
    MAX-ACCESS  read-write
    STATUS      current
    DESCRIPTION
	"The power of phase one"
    ::= { slave8CircuitFour 10}
	
	
slave8CircuitFive OBJECT IDENTIFIER ::= { slave8Circuit 5}	    
slave8CircuitFiveBreaker OBJECT-TYPE
    SYNTAX      DisplayString
    MAX-ACCESS  read-only
    STATUS      current
    DESCRIPTION
	"The power of phase one"
    ::= { slave8CircuitFive 1}
	
slave8CircuitFiveManagementBit OBJECT-TYPE
    SYNTAX      DisplayString
    MAX-ACCESS  read-only
    STATUS      current
    DESCRIPTION
	"The power of phase one"
    ::= { slave8CircuitFive 2}	

slave8CircuitFiveCurrent OBJECT-TYPE
    SYNTAX      DisplayString
    MAX-ACCESS  read-only
    STATUS      current
    DESCRIPTION
	"The power of phase one"
    ::= { slave8CircuitFive 3}

slave8CircuitFiveVoltage OBJECT-TYPE
    SYNTAX      DisplayString
    MAX-ACCESS  read-only
    STATUS      current
    DESCRIPTION
	"The power of phase one"
    ::= { slave8CircuitFive 4}

slave8CircuitFiveEnergy OBJECT-TYPE
    SYNTAX      DisplayString
    MAX-ACCESS  read-only
    STATUS      current
    DESCRIPTION
	"The power of phase one"
    ::= { slave8CircuitFive 5}	
	
slave8CircuitFivePower OBJECT-TYPE
    SYNTAX      DisplayString
    MAX-ACCESS  read-only
    STATUS      current
    DESCRIPTION
	"The power of phase one"
    ::= { slave8CircuitFive 6}
		
slave8CircuitFiveCurrentMin OBJECT-TYPE
    SYNTAX      DisplayString
    MAX-ACCESS  read-write
    STATUS      current
    DESCRIPTION
	"The power of phase one"
    ::= { slave8CircuitFive 7}	
	
slave8CircuitFiveCurrentMinCritical OBJECT-TYPE
    SYNTAX      DisplayString
    MAX-ACCESS  read-write
    STATUS      current
    DESCRIPTION
	"The power of phase one"
    ::= { slave8CircuitFive 8}
	
slave8CircuitFiveCurrentMaxCritical OBJECT-TYPE
    SYNTAX      DisplayString
    MAX-ACCESS  read-write
    STATUS      current
    DESCRIPTION
	"The power of phase one"
    ::= { slave8CircuitFive 9}
	
slave8CircuitFiveCurrentMax OBJECT-TYPE
    SYNTAX      DisplayString
    MAX-ACCESS  read-write
    STATUS      current
    DESCRIPTION
	"The power of phase one"
    ::= { slave8CircuitFive 10}

	
slave8CircuitSix OBJECT IDENTIFIER ::= { slave8Circuit 6}	    
slave8CircuitSixBreaker OBJECT-TYPE
    SYNTAX      DisplayString
    MAX-ACCESS  read-only
    STATUS      current
    DESCRIPTION
	"The power of phase one"
    ::= { slave8CircuitSix 1}
	
slave8CircuitSixManagementBit OBJECT-TYPE
    SYNTAX      DisplayString
    MAX-ACCESS  read-only
    STATUS      current
    DESCRIPTION
	"The power of phase one"
    ::= { slave8CircuitSix 2}	

slave8CircuitSixCurrent OBJECT-TYPE
    SYNTAX      DisplayString
    MAX-ACCESS  read-only
    STATUS      current
    DESCRIPTION
	"The power of phase one"
    ::= { slave8CircuitSix 3}

slave8CircuitSixVoltage OBJECT-TYPE
    SYNTAX      DisplayString
    MAX-ACCESS  read-only
    STATUS      current
    DESCRIPTION
	"The power of phase one"
    ::= { slave8CircuitSix 4}

slave8CircuitSixEnergy OBJECT-TYPE
    SYNTAX      DisplayString
    MAX-ACCESS  read-only
    STATUS      current
    DESCRIPTION
	"The power of phase one"
    ::= { slave8CircuitSix 5}	
	
slave8CircuitSixPower OBJECT-TYPE
    SYNTAX      DisplayString
    MAX-ACCESS  read-only
    STATUS      current
    DESCRIPTION
	"The power of phase one"
    ::= { slave8CircuitSix 6}
	
slave8CircuitSixCurrentMin OBJECT-TYPE
    SYNTAX      DisplayString
    MAX-ACCESS  read-write
    STATUS      current
    DESCRIPTION
	"The power of phase one"
    ::= { slave8CircuitSix 7}	
	
slave8CircuitSixCurrentMinCritical OBJECT-TYPE
    SYNTAX      DisplayString
    MAX-ACCESS  read-write
    STATUS      current
    DESCRIPTION
	"The power of phase one"
    ::= { slave8CircuitSix 8}
	
slave8CircuitSixCurrentMaxCritical OBJECT-TYPE
    SYNTAX      DisplayString
    MAX-ACCESS  read-write
    STATUS      current
    DESCRIPTION
	"The power of phase one"
    ::= { slave8CircuitSix 9}
	
slave8CircuitSixCurrentMax OBJECT-TYPE
    SYNTAX      DisplayString
    MAX-ACCESS  read-write
    STATUS      current
    DESCRIPTION
	"The power of phase one"
    ::= { slave8CircuitSix 10}

	
-------------------------------slave8 sensor------------------------	
slave8Sensor OBJECT IDENTIFIER ::= { slave8 4}
slave8SensorTemperatureOne OBJECT-TYPE
    SYNTAX      DisplayString
    MAX-ACCESS  read-only
    STATUS      current
    DESCRIPTION
	"This is the first device."
    ::= { slave8Sensor 1}
	
slave8SensorTemperatureTwo OBJECT-TYPE
    SYNTAX      DisplayString
    MAX-ACCESS  read-only
    STATUS      current
    DESCRIPTION
	"This is the first device."
    ::= { slave8Sensor 2}

slave8SensorHumidityOne OBJECT-TYPE
    SYNTAX      DisplayString
    MAX-ACCESS  read-only
    STATUS      current
    DESCRIPTION
	"This is the first device."
    ::= { slave8Sensor 3}

slave8SensorHumidityTwo OBJECT-TYPE
    SYNTAX      DisplayString
    MAX-ACCESS  read-only
    STATUS      current
    DESCRIPTION
	"This is the first device."
    ::= { slave8Sensor 4}	

slave8SensorDoorOne OBJECT-TYPE
    SYNTAX      DisplayString
    MAX-ACCESS  read-only
    STATUS      current
    DESCRIPTION
	"This is the first device."
    ::= { slave8Sensor 5}

slave8SensorDoorTwo OBJECT-TYPE
    SYNTAX      DisplayString
    MAX-ACCESS  read-only
    STATUS      current
    DESCRIPTION
	"This is the first device."
    ::= { slave8Sensor 6}	
	
slave8SensorSmoke OBJECT-TYPE
    SYNTAX      DisplayString
    MAX-ACCESS  read-only
    STATUS      current
    DESCRIPTION
	"This is the first device."
    ::= { slave8Sensor 7}
	
slave8SensorWater OBJECT-TYPE
    SYNTAX      DisplayString
    MAX-ACCESS  read-only
    STATUS      current
    DESCRIPTION
	"This is the first device."
    ::= { slave8Sensor 8}
	
slave8SensorTemperatureOneMin OBJECT-TYPE
    SYNTAX      DisplayString
    MAX-ACCESS  read-write
    STATUS      current
    DESCRIPTION
	"This is the first device."
    ::= { slave8Sensor 9}
	
slave8SensorTemperatureOneMinCritical OBJECT-TYPE
    SYNTAX      DisplayString
    MAX-ACCESS  read-write
    STATUS      current
    DESCRIPTION
	"This is the first device."
    ::= { slave8Sensor 10}	
	
slave8SensorTemperatureOneMaxCritical OBJECT-TYPE
    SYNTAX      DisplayString
    MAX-ACCESS  read-write
    STATUS      current
    DESCRIPTION
	"This is the first device."
    ::= { slave8Sensor 11}
	
slave8SensorTemperatureOneMax OBJECT-TYPE
    SYNTAX      DisplayString
    MAX-ACCESS  read-write
    STATUS      current
    DESCRIPTION
	"This is the first device."
    ::= { slave8Sensor 12}

slave8SensorTemperatureTwoMin OBJECT-TYPE
    SYNTAX      DisplayString
    MAX-ACCESS  read-write
    STATUS      current
    DESCRIPTION
	"This is the first device."
    ::= { slave8Sensor 13}
	
slave8SensorTemperatureTwoMinCritical OBJECT-TYPE
    SYNTAX      DisplayString
    MAX-ACCESS  read-write
    STATUS      current
    DESCRIPTION
	"This is the first device."
    ::= { slave8Sensor 14}	
	
slave8SensorTemperatureTwoMaxCritical OBJECT-TYPE
    SYNTAX      DisplayString
    MAX-ACCESS  read-write
    STATUS      current
    DESCRIPTION
	"This is the first device."
    ::= { slave8Sensor 15}
	
slave8SensorTemperatureTwoMax OBJECT-TYPE
    SYNTAX      DisplayString
    MAX-ACCESS  read-write
    STATUS      current
    DESCRIPTION
	"This is the first device."
    ::= { slave8Sensor 16}
	
slave8SensorHumidityOneMin OBJECT-TYPE
    SYNTAX      DisplayString
    MAX-ACCESS  read-write
    STATUS      current
    DESCRIPTION
	"This is the first device."
    ::= { slave8Sensor 17}
	
slave8SensorHumidityOneMinCritical OBJECT-TYPE
    SYNTAX      DisplayString
    MAX-ACCESS  read-write
    STATUS      current
    DESCRIPTION
	"This is the first device."
    ::= { slave8Sensor 18}	
	
slave8SensorHumidityOneMaxCritical OBJECT-TYPE
    SYNTAX      DisplayString
    MAX-ACCESS  read-write
    STATUS      current
    DESCRIPTION
	"This is the first device."
    ::= { slave8Sensor 19}
	
slave8SensorHumidityOneMax OBJECT-TYPE
    SYNTAX      DisplayString
    MAX-ACCESS  read-write
    STATUS      current
    DESCRIPTION
	"This is the first device."
    ::= { slave8Sensor 20}

slave8SensorHumidityTwoMin OBJECT-TYPE
    SYNTAX      DisplayString
    MAX-ACCESS  read-write
    STATUS      current
    DESCRIPTION
	"This is the first device."
    ::= { slave8Sensor 21}
	
slave8SensorHumidityTwoMinCritical OBJECT-TYPE
    SYNTAX      DisplayString
    MAX-ACCESS  read-write
    STATUS      current
    DESCRIPTION
	"This is the first device."
    ::= { slave8Sensor 22}	
	
slave8SensorHumidityTwoMaxCritical OBJECT-TYPE
    SYNTAX      DisplayString
    MAX-ACCESS  read-write
    STATUS      current
    DESCRIPTION
	"This is the first device."
    ::= { slave8Sensor 23}
	
slave8SensorHumidityTwoMax OBJECT-TYPE
    SYNTAX      DisplayString
    MAX-ACCESS  read-write
    STATUS      current
    DESCRIPTION
	"This is the first device."
    ::= { slave8Sensor 24}
	
-------------------------------slave8 output name------------------------	
slave8OutputName OBJECT IDENTIFIER ::= { slave8 5}
slave8OutputNameOne OBJECT-TYPE
    SYNTAX      DisplayString
    MAX-ACCESS  read-write
    STATUS      current
    DESCRIPTION
	"The first output name of slave8"
    ::= { slave8OutputName 1}

slave8OutputNameTwo OBJECT-TYPE
    SYNTAX      DisplayString
    MAX-ACCESS  read-write
    STATUS      current
    DESCRIPTION
	"The second output name of slave8"
    ::= { slave8OutputName 2}

slave8OutputNameThree OBJECT-TYPE
    SYNTAX      DisplayString
    MAX-ACCESS  read-write
    STATUS      current
    DESCRIPTION
	"The second output name of slave8"
    ::= { slave8OutputName 3}

slave8OutputNameFour OBJECT-TYPE
    SYNTAX      DisplayString
    MAX-ACCESS  read-write
    STATUS      current
    DESCRIPTION
	"The second output name of slave8"
    ::= { slave8OutputName 4}

slave8OutputNameFive OBJECT-TYPE
    SYNTAX      DisplayString
    MAX-ACCESS  read-write
    STATUS      current
    DESCRIPTION
	"The second output name of slave8"
    ::= { slave8OutputName 5}

slave8OutputNameSix OBJECT-TYPE
    SYNTAX      DisplayString
    MAX-ACCESS  read-write
    STATUS      current
    DESCRIPTION
	"The second output name of slave8"
    ::= { slave8OutputName 6}

slave8OutputNameSeven OBJECT-TYPE
    SYNTAX      DisplayString
    MAX-ACCESS  read-write
    STATUS      current
    DESCRIPTION
	"The second output name of slave8"
    ::= { slave8OutputName 7}

slave8OutputNameEight OBJECT-TYPE
    SYNTAX      DisplayString
    MAX-ACCESS  read-write
    STATUS      current
    DESCRIPTION
	"The second output name of slave8"
    ::= { slave8OutputName 8}

slave8OutputNameNine OBJECT-TYPE
    SYNTAX      DisplayString
    MAX-ACCESS  read-write
    STATUS      current
    DESCRIPTION
	"The second output name of slave8"
    ::= { slave8OutputName 9}

slave8OutputNameTen OBJECT-TYPE
    SYNTAX      DisplayString
    MAX-ACCESS  read-write
    STATUS      current
    DESCRIPTION
	"The second output name of slave8"
    ::= { slave8OutputName 10}

slave8OutputNameEleven OBJECT-TYPE
    SYNTAX      DisplayString
    MAX-ACCESS  read-write
    STATUS      current
    DESCRIPTION
	"The second output name of slave8"
    ::= { slave8OutputName 11}

slave8OutputNameTwel OBJECT-TYPE
    SYNTAX      DisplayString
    MAX-ACCESS  read-write
    STATUS      current
    DESCRIPTION
	"The second output name of slave8"
    ::= { slave8OutputName 12}

slave8OutputNameThirteen OBJECT-TYPE
    SYNTAX      DisplayString
    MAX-ACCESS  read-write
    STATUS      current
    DESCRIPTION
	"The second output name of slave8"
    ::= { slave8OutputName 13}

slave8OutputNameFourteen OBJECT-TYPE
    SYNTAX      DisplayString
    MAX-ACCESS  read-write
    STATUS      current
    DESCRIPTION
	"The second output name of slave8"
    ::= { slave8OutputName 14}

slave8OutputNameFifteen OBJECT-TYPE
    SYNTAX      DisplayString
    MAX-ACCESS  read-write
    STATUS      current
    DESCRIPTION
	"The second output name of slave8"
    ::= { slave8OutputName 15}

slave8OutputNameSixteen OBJECT-TYPE
    SYNTAX      DisplayString
    MAX-ACCESS  read-write
    STATUS      current
    DESCRIPTION
	"The second output name of slave8"
    ::= { slave8OutputName 16}

slave8OutputNameSeventeen OBJECT-TYPE
    SYNTAX      DisplayString
    MAX-ACCESS  read-write
    STATUS      current
    DESCRIPTION
	"The second output name of slave8"
    ::= { slave8OutputName 17}

slave8OutputNameEighteen OBJECT-TYPE
    SYNTAX      DisplayString
    MAX-ACCESS  read-write
    STATUS      current
    DESCRIPTION
	"The second output name of slave8"
    ::= { slave8OutputName 18}
	
slave8OutputNameNineteen OBJECT-TYPE
    SYNTAX      DisplayString
    MAX-ACCESS  read-write
    STATUS      current
    DESCRIPTION
	"The second output name of slave8"
    ::= { slave8OutputName 19}
	
slave8OutputNametwenty OBJECT-TYPE
    SYNTAX      DisplayString
    MAX-ACCESS  read-write
    STATUS      current
    DESCRIPTION
	"The second output name of slave8"
    ::= { slave8OutputName 20}
	
slave8OutputNameTwentyone OBJECT-TYPE
    SYNTAX      DisplayString
    MAX-ACCESS  read-write
    STATUS      current
    DESCRIPTION
	"The second output name of slave8"
    ::= { slave8OutputName 21}
	
slave8OutputNameTwentyonetwo OBJECT-TYPE
    SYNTAX      DisplayString
    MAX-ACCESS  read-write
    STATUS      current
    DESCRIPTION
	"The second output name of slave8"
    ::= { slave8OutputName 22}
	
slave8OutputNameTwentythree OBJECT-TYPE
    SYNTAX      DisplayString
    MAX-ACCESS  read-write
    STATUS      current
    DESCRIPTION
	"The second output name of slave8"
    ::= { slave8OutputName 23}
	
slave8OutputNameTwentyfour OBJECT-TYPE
    SYNTAX      DisplayString
    MAX-ACCESS  read-write
    STATUS      current
    DESCRIPTION
	"The second output name of slave8"
    ::= { slave8OutputName 24}
	
slave8OutputNameTwentyfive OBJECT-TYPE
    SYNTAX      DisplayString
    MAX-ACCESS  read-write
    STATUS      current
    DESCRIPTION
	"The second output name of slave8"
    ::= { slave8OutputName 25}
	
slave8OutputNameTwentysix OBJECT-TYPE
    SYNTAX      DisplayString
    MAX-ACCESS  read-write
    STATUS      current
    DESCRIPTION
	"The second output name of slave8"
    ::= { slave8OutputName 26}
	
slave8OutputNameTwentyseven OBJECT-TYPE
    SYNTAX      DisplayString
    MAX-ACCESS  read-write
    STATUS      current
    DESCRIPTION
	"The second output name of slave8"
    ::= { slave8OutputName 27}
	
slave8OutputNameTwentyeight OBJECT-TYPE
    SYNTAX      DisplayString
    MAX-ACCESS  read-write
    STATUS      current
    DESCRIPTION
	"The second output name of slave8"
    ::= { slave8OutputName 28}	
slave8OutputNameTwentynine OBJECT-TYPE
    SYNTAX      DisplayString
    MAX-ACCESS  read-write
    STATUS      current
    DESCRIPTION
	"The second output name of slave8"
    ::= { slave8OutputName 29}
	
slave8OutputNameThirty OBJECT-TYPE
    SYNTAX      DisplayString
    MAX-ACCESS  read-write
    STATUS      current
    DESCRIPTION
	"The second output name of slave8"
    ::= { slave8OutputName 30}
	
slave8OutputNameThirtyone OBJECT-TYPE
    SYNTAX      DisplayString
    MAX-ACCESS  read-write
    STATUS      current
    DESCRIPTION
	"The second output name of slave8"
    ::= { slave8OutputName 31}
	
slave8OutputNameThirtytwo OBJECT-TYPE
    SYNTAX      DisplayString
    MAX-ACCESS  read-write
    STATUS      current
    DESCRIPTION
	"The second output name of slave8"
    ::= { slave8OutputName 32}
	
slave8OutputNameThirtythree OBJECT-TYPE
    SYNTAX      DisplayString
    MAX-ACCESS  read-write
    STATUS      current
    DESCRIPTION
	"The second output name of slave8"
    ::= { slave8OutputName 33}
	
slave8OutputNameThirtyfour OBJECT-TYPE
    SYNTAX      DisplayString
    MAX-ACCESS  read-write
    STATUS      current
    DESCRIPTION
	"The second output name of slave8"
    ::= { slave8OutputName 34}
	
slave8OutputNameThirtyfive OBJECT-TYPE
    SYNTAX      DisplayString
    MAX-ACCESS  read-write
    STATUS      current
    DESCRIPTION
	"The second output name of slave8"
    ::= { slave8OutputName 35}
	
slave8OutputNameThirtysix OBJECT-TYPE
    SYNTAX      DisplayString
    MAX-ACCESS  read-write
    STATUS      current
    DESCRIPTION
	"The second output name of slave8"
    ::= { slave8OutputName 36}
	
slave8OutputNameThirtyseven OBJECT-TYPE
    SYNTAX      DisplayString
    MAX-ACCESS  read-write
    STATUS      current
    DESCRIPTION
	"The second output name of slave8"
    ::= { slave8OutputName 37}
	
slave8OutputNameThirtyeight OBJECT-TYPE
    SYNTAX      DisplayString
    MAX-ACCESS  read-write
    STATUS      current
    DESCRIPTION
	"The second output name of slave8"
    ::= { slave8OutputName 38}
	
slave8OutputNameThirtynine OBJECT-TYPE
    SYNTAX      DisplayString
    MAX-ACCESS  read-write
    STATUS      current
    DESCRIPTION
	"The second output name of slave8"
    ::= { slave8OutputName 39}
	
slave8OutputNameFourty OBJECT-TYPE
    SYNTAX      DisplayString
    MAX-ACCESS  read-write
    STATUS      current
    DESCRIPTION
	"The second output name of slave8"
    ::= { slave8OutputName 40}
	
slave8OutputNameFourtyone OBJECT-TYPE
    SYNTAX      DisplayString
    MAX-ACCESS  read-write
    STATUS      current
    DESCRIPTION
	"The second output name of slave8"
    ::= { slave8OutputName 41}
	
slave8OutputNameFourtytwo OBJECT-TYPE
    SYNTAX      DisplayString
    MAX-ACCESS  read-write
    STATUS      current
    DESCRIPTION
	"The second output name of slave8"
    ::= { slave8OutputName 42}	

	
-------------------------------slave8 output delay------------------------	
slave8OutputDelay OBJECT IDENTIFIER ::= { slave8 6}	
slave8OutputDelayOne OBJECT-TYPE
    SYNTAX      DisplayString
    MAX-ACCESS  read-write
    STATUS      current
    DESCRIPTION
	"The first output name of slave8"
    ::= { slave8OutputDelay 1}

slave8OutputDelayTwo OBJECT-TYPE
    SYNTAX      DisplayString
    MAX-ACCESS  read-write
    STATUS      current
    DESCRIPTION
	"The second output name of slave8"
    ::= { slave8OutputDelay 2}

slave8OutputDelayThree OBJECT-TYPE
    SYNTAX      DisplayString
    MAX-ACCESS  read-write
    STATUS      current
    DESCRIPTION
	"The second output name of slave8"
    ::= { slave8OutputDelay 3}

slave8OutputDelayFour OBJECT-TYPE
    SYNTAX      DisplayString
    MAX-ACCESS  read-write
    STATUS      current
    DESCRIPTION
	"The second output name of slave8"
    ::= { slave8OutputDelay 4}

slave8OutputDelayFive OBJECT-TYPE
    SYNTAX      DisplayString
    MAX-ACCESS  read-write
    STATUS      current
    DESCRIPTION
	"The second output name of slave8"
    ::= { slave8OutputDelay 5}

slave8OutputDelaySix OBJECT-TYPE
    SYNTAX      DisplayString
    MAX-ACCESS  read-write
    STATUS      current
    DESCRIPTION
	"The second output name of slave8"
    ::= { slave8OutputDelay 6}

slave8OutputDelaySeven OBJECT-TYPE
    SYNTAX      DisplayString
    MAX-ACCESS  read-write
    STATUS      current
    DESCRIPTION
	"The second output name of slave8"
    ::= { slave8OutputDelay 7}

slave8OutputDelayEight OBJECT-TYPE
    SYNTAX      DisplayString
    MAX-ACCESS  read-write
    STATUS      current
    DESCRIPTION
	"The second output name of slave8"
    ::= { slave8OutputDelay 8}

slave8OutputDelayNine OBJECT-TYPE
    SYNTAX      DisplayString
    MAX-ACCESS  read-write
    STATUS      current
    DESCRIPTION
	"The second output name of slave8"
    ::= { slave8OutputDelay 9}

slave8OutputDelayTen OBJECT-TYPE
    SYNTAX      DisplayString
    MAX-ACCESS  read-write
    STATUS      current
    DESCRIPTION
	"The second output name of slave8"
    ::= { slave8OutputDelay 10}

slave8OutputDelayEleven OBJECT-TYPE
    SYNTAX      DisplayString
    MAX-ACCESS  read-write
    STATUS      current
    DESCRIPTION
	"The second output name of slave8"
    ::= { slave8OutputDelay 11}

slave8OutputDelayTwel OBJECT-TYPE
    SYNTAX      DisplayString
    MAX-ACCESS  read-write
    STATUS      current
    DESCRIPTION
	"The second output name of slave8"
    ::= { slave8OutputDelay 12}

slave8OutputDelayThirteen OBJECT-TYPE
    SYNTAX      DisplayString
    MAX-ACCESS  read-write
    STATUS      current
    DESCRIPTION
	"The second output name of slave8"
    ::= { slave8OutputDelay 13}

slave8OutputDelayFourteen OBJECT-TYPE
    SYNTAX      DisplayString
    MAX-ACCESS  read-write
    STATUS      current
    DESCRIPTION
	"The second output name of slave8"
    ::= { slave8OutputDelay 14}

slave8OutputDelayFifteen OBJECT-TYPE
    SYNTAX      DisplayString
    MAX-ACCESS  read-write
    STATUS      current
    DESCRIPTION
	"The second output name of slave8"
    ::= { slave8OutputDelay 15}

slave8OutputDelaySixteen OBJECT-TYPE
    SYNTAX      DisplayString
    MAX-ACCESS  read-write
    STATUS      current
    DESCRIPTION
	"The second output name of slave8"
    ::= { slave8OutputDelay 16}

slave8OutputDelaySeventeen OBJECT-TYPE
    SYNTAX      DisplayString
    MAX-ACCESS  read-write
    STATUS      current
    DESCRIPTION
	"The second output name of slave8"
    ::= { slave8OutputDelay 17}

slave8OutputDelayEighteen OBJECT-TYPE
    SYNTAX      DisplayString
    MAX-ACCESS  read-write
    STATUS      current
    DESCRIPTION
	"The second output name of slave8"
    ::= { slave8OutputDelay 18}
	
slave8OutputDelayNineteen OBJECT-TYPE
    SYNTAX      DisplayString
    MAX-ACCESS  read-write
    STATUS      current
    DESCRIPTION
	"The second output name of slave8"
    ::= { slave8OutputDelay 19}
	
slave8OutputDelaytwenty OBJECT-TYPE
    SYNTAX      DisplayString
    MAX-ACCESS  read-write
    STATUS      current
    DESCRIPTION
	"The second output name of slave8"
    ::= { slave8OutputDelay 20}
	
slave8OutputDelayTwentyone OBJECT-TYPE
    SYNTAX      DisplayString
    MAX-ACCESS  read-write
    STATUS      current
    DESCRIPTION
	"The second output name of slave8"
    ::= { slave8OutputDelay 21}
	
slave8OutputDelayTwentyonetwo OBJECT-TYPE
    SYNTAX      DisplayString
    MAX-ACCESS  read-write
    STATUS      current
    DESCRIPTION
	"The second output name of slave8"
    ::= { slave8OutputDelay 22}
	
slave8OutputDelayTwentythree OBJECT-TYPE
    SYNTAX      DisplayString
    MAX-ACCESS  read-write
    STATUS      current
    DESCRIPTION
	"The second output name of slave8"
    ::= { slave8OutputDelay 23}
	
slave8OutputDelayTwentyfour OBJECT-TYPE
    SYNTAX      DisplayString
    MAX-ACCESS  read-write
    STATUS      current
    DESCRIPTION
	"The second output name of slave8"
    ::= { slave8OutputDelay 24}
	
slave8OutputDelayTwentyfive OBJECT-TYPE
    SYNTAX      DisplayString
    MAX-ACCESS  read-write
    STATUS      current
    DESCRIPTION
	"The second output name of slave8"
    ::= { slave8OutputDelay 25}
	
slave8OutputDelayTwentysix OBJECT-TYPE
    SYNTAX      DisplayString
    MAX-ACCESS  read-write
    STATUS      current
    DESCRIPTION
	"The second output name of slave8"
    ::= { slave8OutputDelay 26}
	
slave8OutputDelayTwentyseven OBJECT-TYPE
    SYNTAX      DisplayString
    MAX-ACCESS  read-write
    STATUS      current
    DESCRIPTION
	"The second output name of slave8"
    ::= { slave8OutputDelay 27}
	
slave8OutputDelayTwentyeight OBJECT-TYPE
    SYNTAX      DisplayString
    MAX-ACCESS  read-write
    STATUS      current
    DESCRIPTION
	"The second output name of slave8"
    ::= { slave8OutputDelay 28}	
slave8OutputDelayTwentynine OBJECT-TYPE
    SYNTAX      DisplayString
    MAX-ACCESS  read-write
    STATUS      current
    DESCRIPTION
	"The second output name of slave8"
    ::= { slave8OutputDelay 29}
	
slave8OutputDelayThirty OBJECT-TYPE
    SYNTAX      DisplayString
    MAX-ACCESS  read-write
    STATUS      current
    DESCRIPTION
	"The second output name of slave8"
    ::= { slave8OutputDelay 30}
	
slave8OutputDelayThirtyone OBJECT-TYPE
    SYNTAX      DisplayString
    MAX-ACCESS  read-write
    STATUS      current
    DESCRIPTION
	"The second output name of slave8"
    ::= { slave8OutputDelay 31}
	
slave8OutputDelayThirtytwo OBJECT-TYPE
    SYNTAX      DisplayString
    MAX-ACCESS  read-write
    STATUS      current
    DESCRIPTION
	"The second output name of slave8"
    ::= { slave8OutputDelay 32}
	
slave8OutputDelayThirtythree OBJECT-TYPE
    SYNTAX      DisplayString
    MAX-ACCESS  read-write
    STATUS      current
    DESCRIPTION
	"The second output name of slave8"
    ::= { slave8OutputDelay 33}
	
slave8OutputDelayThirtyfour OBJECT-TYPE
    SYNTAX      DisplayString
    MAX-ACCESS  read-write
    STATUS      current
    DESCRIPTION
	"The second output name of slave8"
    ::= { slave8OutputDelay 34}
	
slave8OutputDelayThirtyfive OBJECT-TYPE
    SYNTAX      DisplayString
    MAX-ACCESS  read-write
    STATUS      current
    DESCRIPTION
	"The second output name of slave8"
    ::= { slave8OutputDelay 35}
	
slave8OutputDelayThirtysix OBJECT-TYPE
    SYNTAX      DisplayString
    MAX-ACCESS  read-write
    STATUS      current
    DESCRIPTION
	"The second output name of slave8"
    ::= { slave8OutputDelay 36}
	
slave8OutputDelayThirtyseven OBJECT-TYPE
    SYNTAX      DisplayString
    MAX-ACCESS  read-write
    STATUS      current
    DESCRIPTION
	"The second output name of slave8"
    ::= { slave8OutputDelay 37}
	
slave8OutputDelayThirtyeight OBJECT-TYPE
    SYNTAX      DisplayString
    MAX-ACCESS  read-write
    STATUS      current
    DESCRIPTION
	"The second output name of slave8"
    ::= { slave8OutputDelay 38}
	
slave8OutputDelayThirtynine OBJECT-TYPE
    SYNTAX      DisplayString
    MAX-ACCESS  read-write
    STATUS      current
    DESCRIPTION
	"The second output name of slave8"
    ::= { slave8OutputDelay 39}
	
slave8OutputDelayFourty OBJECT-TYPE
    SYNTAX      DisplayString
    MAX-ACCESS  read-write
    STATUS      current
    DESCRIPTION
	"The second output name of slave8"
    ::= { slave8OutputDelay 40}
	
slave8OutputDelayFourtyone OBJECT-TYPE
    SYNTAX      DisplayString
    MAX-ACCESS  read-write
    STATUS      current
    DESCRIPTION
	"The second output name of slave8"
    ::= { slave8OutputDelay 41}
	
slave8OutputDelayFourtytwo OBJECT-TYPE
    SYNTAX      DisplayString
    MAX-ACCESS  read-write
    STATUS      current
    DESCRIPTION
	"The second output name of slave8"
    ::= { slave8OutputDelay 42}

	
-------------------------------slave8 output switch------------------------	
slave8OutputSwitch OBJECT IDENTIFIER ::= { slave8 7}		
slave8OutputSwitchOne OBJECT-TYPE
    SYNTAX      DisplayString
    MAX-ACCESS  read-write
    STATUS      current
    DESCRIPTION
	"The first output name of slave8"
    ::= { slave8OutputSwitch 1}

slave8OutputSwitchTwo OBJECT-TYPE
    SYNTAX      DisplayString
    MAX-ACCESS  read-write
    STATUS      current
    DESCRIPTION
	"The second output name of slave8"
    ::= { slave8OutputSwitch 2}

slave8OutputSwitchThree OBJECT-TYPE
    SYNTAX      DisplayString
    MAX-ACCESS  read-write
    STATUS      current
    DESCRIPTION
	"The second output name of slave8"
    ::= { slave8OutputSwitch 3}

slave8OutputSwitchFour OBJECT-TYPE
    SYNTAX      DisplayString
    MAX-ACCESS  read-write
    STATUS      current
    DESCRIPTION
	"The second output name of slave8"
    ::= { slave8OutputSwitch 4}

slave8OutputSwitchFive OBJECT-TYPE
    SYNTAX      DisplayString
    MAX-ACCESS  read-write
    STATUS      current
    DESCRIPTION
	"The second output name of slave8"
    ::= { slave8OutputSwitch 5}

slave8OutputSwitchSix OBJECT-TYPE
    SYNTAX      DisplayString
    MAX-ACCESS  read-write
    STATUS      current
    DESCRIPTION
	"The second output name of slave8"
    ::= { slave8OutputSwitch 6}

slave8OutputSwitchSeven OBJECT-TYPE
    SYNTAX      DisplayString
    MAX-ACCESS  read-write
    STATUS      current
    DESCRIPTION
	"The second output name of slave8"
    ::= { slave8OutputSwitch 7}

slave8OutputSwitchEight OBJECT-TYPE
    SYNTAX      DisplayString
    MAX-ACCESS  read-write
    STATUS      current
    DESCRIPTION
	"The second output name of slave8"
    ::= { slave8OutputSwitch 8}

slave8OutputSwitchNine OBJECT-TYPE
    SYNTAX      DisplayString
    MAX-ACCESS  read-write
    STATUS      current
    DESCRIPTION
	"The second output name of slave8"
    ::= { slave8OutputSwitch 9}

slave8OutputSwitchTen OBJECT-TYPE
    SYNTAX      DisplayString
    MAX-ACCESS  read-write
    STATUS      current
    DESCRIPTION
	"The second output name of slave8"
    ::= { slave8OutputSwitch 10}

slave8OutputSwitchEleven OBJECT-TYPE
    SYNTAX      DisplayString
    MAX-ACCESS  read-write
    STATUS      current
    DESCRIPTION
	"The second output name of slave8"
    ::= { slave8OutputSwitch 11}

slave8OutputSwitchTwel OBJECT-TYPE
    SYNTAX      DisplayString
    MAX-ACCESS  read-write
    STATUS      current
    DESCRIPTION
	"The second output name of slave8"
    ::= { slave8OutputSwitch 12}

slave8OutputSwitchThirteen OBJECT-TYPE
    SYNTAX      DisplayString
    MAX-ACCESS  read-write
    STATUS      current
    DESCRIPTION
	"The second output name of slave8"
    ::= { slave8OutputSwitch 13}

slave8OutputSwitchFourteen OBJECT-TYPE
    SYNTAX      DisplayString
    MAX-ACCESS  read-write
    STATUS      current
    DESCRIPTION
	"The second output name of slave8"
    ::= { slave8OutputSwitch 14}

slave8OutputSwitchFifteen OBJECT-TYPE
    SYNTAX      DisplayString
    MAX-ACCESS  read-write
    STATUS      current
    DESCRIPTION
	"The second output name of slave8"
    ::= { slave8OutputSwitch 15}

slave8OutputSwitchSixteen OBJECT-TYPE
    SYNTAX      DisplayString
    MAX-ACCESS  read-write
    STATUS      current
    DESCRIPTION
	"The second output name of slave8"
    ::= { slave8OutputSwitch 16}

slave8OutputSwitchSeventeen OBJECT-TYPE
    SYNTAX      DisplayString
    MAX-ACCESS  read-write
    STATUS      current
    DESCRIPTION
	"The second output name of slave8"
    ::= { slave8OutputSwitch 17}

slave8OutputSwitchEighteen OBJECT-TYPE
    SYNTAX      DisplayString
    MAX-ACCESS  read-write
    STATUS      current
    DESCRIPTION
	"The second output name of slave8"
    ::= { slave8OutputSwitch 18}
	
slave8OutputSwitchNineteen OBJECT-TYPE
    SYNTAX      DisplayString
    MAX-ACCESS  read-write
    STATUS      current
    DESCRIPTION
	"The second output name of slave8"
    ::= { slave8OutputSwitch 19}
	
slave8OutputSwitchtwenty OBJECT-TYPE
    SYNTAX      DisplayString
    MAX-ACCESS  read-write
    STATUS      current
    DESCRIPTION
	"The second output name of slave8"
    ::= { slave8OutputSwitch 20}
	
slave8OutputSwitchTwentyone OBJECT-TYPE
    SYNTAX      DisplayString
    MAX-ACCESS  read-write
    STATUS      current
    DESCRIPTION
	"The second output name of slave8"
    ::= { slave8OutputSwitch 21}
	
slave8OutputSwitchTwentyonetwo OBJECT-TYPE
    SYNTAX      DisplayString
    MAX-ACCESS  read-write
    STATUS      current
    DESCRIPTION
	"The second output name of slave8"
    ::= { slave8OutputSwitch 22}
	
slave8OutputSwitchTwentythree OBJECT-TYPE
    SYNTAX      DisplayString
    MAX-ACCESS  read-write
    STATUS      current
    DESCRIPTION
	"The second output name of slave8"
    ::= { slave8OutputSwitch 23}
	
slave8OutputSwitchTwentyfour OBJECT-TYPE
    SYNTAX      DisplayString
    MAX-ACCESS  read-write
    STATUS      current
    DESCRIPTION
	"The second output name of slave8"
    ::= { slave8OutputSwitch 24}
	
slave8OutputSwitchTwentyfive OBJECT-TYPE
    SYNTAX      DisplayString
    MAX-ACCESS  read-write
    STATUS      current
    DESCRIPTION
	"The second output name of slave8"
    ::= { slave8OutputSwitch 25}
	
slave8OutputSwitchTwentysix OBJECT-TYPE
    SYNTAX      DisplayString
    MAX-ACCESS  read-write
    STATUS      current
    DESCRIPTION
	"The second output name of slave8"
    ::= { slave8OutputSwitch 26}
	
slave8OutputSwitchTwentyseven OBJECT-TYPE
    SYNTAX      DisplayString
    MAX-ACCESS  read-write
    STATUS      current
    DESCRIPTION
	"The second output name of slave8"
    ::= { slave8OutputSwitch 27}
	
slave8OutputSwitchTwentyeight OBJECT-TYPE
    SYNTAX      DisplayString
    MAX-ACCESS  read-write
    STATUS      current
    DESCRIPTION
	"The second output name of slave8"
    ::= { slave8OutputSwitch 28}	
slave8OutputSwitchTwentynine OBJECT-TYPE
    SYNTAX      DisplayString
    MAX-ACCESS  read-write
    STATUS      current
    DESCRIPTION
	"The second output name of slave8"
    ::= { slave8OutputSwitch 29}
	
slave8OutputSwitchThirty OBJECT-TYPE
    SYNTAX      DisplayString
    MAX-ACCESS  read-write
    STATUS      current
    DESCRIPTION
	"The second output name of slave8"
    ::= { slave8OutputSwitch 30}
	
slave8OutputSwitchThirtyone OBJECT-TYPE
    SYNTAX      DisplayString
    MAX-ACCESS  read-write
    STATUS      current
    DESCRIPTION
	"The second output name of slave8"
    ::= { slave8OutputSwitch 31}
	
slave8OutputSwitchThirtytwo OBJECT-TYPE
    SYNTAX      DisplayString
    MAX-ACCESS  read-write
    STATUS      current
    DESCRIPTION
	"The second output name of slave8"
    ::= { slave8OutputSwitch 32}
	
slave8OutputSwitchThirtythree OBJECT-TYPE
    SYNTAX      DisplayString
    MAX-ACCESS  read-write
    STATUS      current
    DESCRIPTION
	"The second output name of slave8"
    ::= { slave8OutputSwitch 33}
	
slave8OutputSwitchThirtyfour OBJECT-TYPE
    SYNTAX      DisplayString
    MAX-ACCESS  read-write
    STATUS      current
    DESCRIPTION
	"The second output name of slave8"
    ::= { slave8OutputSwitch 34}
	
slave8OutputSwitchThirtyfive OBJECT-TYPE
    SYNTAX      DisplayString
    MAX-ACCESS  read-write
    STATUS      current
    DESCRIPTION
	"The second output name of slave8"
    ::= { slave8OutputSwitch 35}
	
slave8OutputSwitchThirtysix OBJECT-TYPE
    SYNTAX      DisplayString
    MAX-ACCESS  read-write
    STATUS      current
    DESCRIPTION
	"The second output name of slave8"
    ::= { slave8OutputSwitch 36}
	
slave8OutputSwitchThirtyseven OBJECT-TYPE
    SYNTAX      DisplayString
    MAX-ACCESS  read-write
    STATUS      current
    DESCRIPTION
	"The second output name of slave8"
    ::= { slave8OutputSwitch 37}
	
slave8OutputSwitchThirtyeight OBJECT-TYPE
    SYNTAX      DisplayString
    MAX-ACCESS  read-write
    STATUS      current
    DESCRIPTION
	"The second output name of slave8"
    ::= { slave8OutputSwitch 38}
	
slave8OutputSwitchThirtynine OBJECT-TYPE
    SYNTAX      DisplayString
    MAX-ACCESS  read-write
    STATUS      current
    DESCRIPTION
	"The second output name of slave8"
    ::= { slave8OutputSwitch 39}
	
slave8OutputSwitchFourty OBJECT-TYPE
    SYNTAX      DisplayString
    MAX-ACCESS  read-write
    STATUS      current
    DESCRIPTION
	"The second output name of slave8"
    ::= { slave8OutputSwitch 40}
	
slave8OutputSwitchFourtyone OBJECT-TYPE
    SYNTAX      DisplayString
    MAX-ACCESS  read-write
    STATUS      current
    DESCRIPTION
	"The second output name of slave8"
    ::= { slave8OutputSwitch 41}
	
slave8OutputSwitchFourtytwo OBJECT-TYPE
    SYNTAX      DisplayString
    MAX-ACCESS  read-write
    STATUS      current
    DESCRIPTION
	"The second output name of slave8"
    ::= { slave8OutputSwitch 42}

	
-------------------------------slave8 output current------------------------	
slave8OutputCurrent OBJECT IDENTIFIER ::= { slave8 8}		
slave8OutputCurrentValue OBJECT IDENTIFIER ::= { slave8OutputCurrent 1}	

slave8OutputCurrentValueOne OBJECT-TYPE
    SYNTAX      DisplayString
    MAX-ACCESS  read-write
    STATUS      current
    DESCRIPTION
	"The first output name of slave8"
    ::= { slave8OutputCurrentValue 1}

slave8OutputCurrentValueTwo OBJECT-TYPE
    SYNTAX      DisplayString
    MAX-ACCESS  read-write
    STATUS      current
    DESCRIPTION
	"The second output name of slave8"
    ::= { slave8OutputCurrentValue 2}

slave8OutputCurrentValueThree OBJECT-TYPE
    SYNTAX      DisplayString
    MAX-ACCESS  read-write
    STATUS      current
    DESCRIPTION
	"The second output name of slave8"
    ::= { slave8OutputCurrentValue 3}

slave8OutputCurrentValueFour OBJECT-TYPE
    SYNTAX      DisplayString
    MAX-ACCESS  read-write
    STATUS      current
    DESCRIPTION
	"The second output name of slave8"
    ::= { slave8OutputCurrentValue 4}

slave8OutputCurrentValueFive OBJECT-TYPE
    SYNTAX      DisplayString
    MAX-ACCESS  read-write
    STATUS      current
    DESCRIPTION
	"The second output name of slave8"
    ::= { slave8OutputCurrentValue 5}

slave8OutputCurrentValueSix OBJECT-TYPE
    SYNTAX      DisplayString
    MAX-ACCESS  read-write
    STATUS      current
    DESCRIPTION
	"The second output name of slave8"
    ::= { slave8OutputCurrentValue 6}

slave8OutputCurrentValueSeven OBJECT-TYPE
    SYNTAX      DisplayString
    MAX-ACCESS  read-write
    STATUS      current
    DESCRIPTION
	"The second output name of slave8"
    ::= { slave8OutputCurrentValue 7}

slave8OutputCurrentValueEight OBJECT-TYPE
    SYNTAX      DisplayString
    MAX-ACCESS  read-write
    STATUS      current
    DESCRIPTION
	"The second output name of slave8"
    ::= { slave8OutputCurrentValue 8}

slave8OutputCurrentValueNine OBJECT-TYPE
    SYNTAX      DisplayString
    MAX-ACCESS  read-write
    STATUS      current
    DESCRIPTION
	"The second output name of slave8"
    ::= { slave8OutputCurrentValue 9}

slave8OutputCurrentValueTen OBJECT-TYPE
    SYNTAX      DisplayString
    MAX-ACCESS  read-write
    STATUS      current
    DESCRIPTION
	"The second output name of slave8"
    ::= { slave8OutputCurrentValue 10}

slave8OutputCurrentValueEleven OBJECT-TYPE
    SYNTAX      DisplayString
    MAX-ACCESS  read-write
    STATUS      current
    DESCRIPTION
	"The second output name of slave8"
    ::= { slave8OutputCurrentValue 11}

slave8OutputCurrentValueTwel OBJECT-TYPE
    SYNTAX      DisplayString
    MAX-ACCESS  read-write
    STATUS      current
    DESCRIPTION
	"The second output name of slave8"
    ::= { slave8OutputCurrentValue 12}

slave8OutputCurrentValueThirteen OBJECT-TYPE
    SYNTAX      DisplayString
    MAX-ACCESS  read-write
    STATUS      current
    DESCRIPTION
	"The second output name of slave8"
    ::= { slave8OutputCurrentValue 13}

slave8OutputCurrentValueFourteen OBJECT-TYPE
    SYNTAX      DisplayString
    MAX-ACCESS  read-write
    STATUS      current
    DESCRIPTION
	"The second output name of slave8"
    ::= { slave8OutputCurrentValue 14}

slave8OutputCurrentValueFifteen OBJECT-TYPE
    SYNTAX      DisplayString
    MAX-ACCESS  read-write
    STATUS      current
    DESCRIPTION
	"The second output name of slave8"
    ::= { slave8OutputCurrentValue 15}

slave8OutputCurrentValueSixteen OBJECT-TYPE
    SYNTAX      DisplayString
    MAX-ACCESS  read-write
    STATUS      current
    DESCRIPTION
	"The second output name of slave8"
    ::= { slave8OutputCurrentValue 16}

slave8OutputCurrentValueSeventeen OBJECT-TYPE
    SYNTAX      DisplayString
    MAX-ACCESS  read-write
    STATUS      current
    DESCRIPTION
	"The second output name of slave8"
    ::= { slave8OutputCurrentValue 17}

slave8OutputCurrentValueEighteen OBJECT-TYPE
    SYNTAX      DisplayString
    MAX-ACCESS  read-write
    STATUS      current
    DESCRIPTION
	"The second output name of slave8"
    ::= { slave8OutputCurrentValue 18}
	
slave8OutputCurrentValueNineteen OBJECT-TYPE
    SYNTAX      DisplayString
    MAX-ACCESS  read-write
    STATUS      current
    DESCRIPTION
	"The second output name of slave8"
    ::= { slave8OutputCurrentValue 19}
	
slave8OutputCurrentValuetwenty OBJECT-TYPE
    SYNTAX      DisplayString
    MAX-ACCESS  read-write
    STATUS      current
    DESCRIPTION
	"The second output name of slave8"
    ::= { slave8OutputCurrentValue 20}
	
slave8OutputCurrentValueTwentyone OBJECT-TYPE
    SYNTAX      DisplayString
    MAX-ACCESS  read-write
    STATUS      current
    DESCRIPTION
	"The second output name of slave8"
    ::= { slave8OutputCurrentValue 21}
	
slave8OutputCurrentValueTwentyonetwo OBJECT-TYPE
    SYNTAX      DisplayString
    MAX-ACCESS  read-write
    STATUS      current
    DESCRIPTION
	"The second output name of slave8"
    ::= { slave8OutputCurrentValue 22}
	
slave8OutputCurrentValueTwentythree OBJECT-TYPE
    SYNTAX      DisplayString
    MAX-ACCESS  read-write
    STATUS      current
    DESCRIPTION
	"The second output name of slave8"
    ::= { slave8OutputCurrentValue 23}
	
slave8OutputCurrentValueTwentyfour OBJECT-TYPE
    SYNTAX      DisplayString
    MAX-ACCESS  read-write
    STATUS      current
    DESCRIPTION
	"The second output name of slave8"
    ::= { slave8OutputCurrentValue 24}
	
slave8OutputCurrentValueTwentyfive OBJECT-TYPE
    SYNTAX      DisplayString
    MAX-ACCESS  read-write
    STATUS      current
    DESCRIPTION
	"The second output name of slave8"
    ::= { slave8OutputCurrentValue 25}
	
slave8OutputCurrentValueTwentysix OBJECT-TYPE
    SYNTAX      DisplayString
    MAX-ACCESS  read-write
    STATUS      current
    DESCRIPTION
	"The second output name of slave8"
    ::= { slave8OutputCurrentValue 26}
	
slave8OutputCurrentValueTwentyseven OBJECT-TYPE
    SYNTAX      DisplayString
    MAX-ACCESS  read-write
    STATUS      current
    DESCRIPTION
	"The second output name of slave8"
    ::= { slave8OutputCurrentValue 27}
	
slave8OutputCurrentValueTwentyeight OBJECT-TYPE
    SYNTAX      DisplayString
    MAX-ACCESS  read-write
    STATUS      current
    DESCRIPTION
	"The second output name of slave8"
    ::= { slave8OutputCurrentValue 28}	
slave8OutputCurrentValueTwentynine OBJECT-TYPE
    SYNTAX      DisplayString
    MAX-ACCESS  read-write
    STATUS      current
    DESCRIPTION
	"The second output name of slave8"
    ::= { slave8OutputCurrentValue 29}
	
slave8OutputCurrentValueThirty OBJECT-TYPE
    SYNTAX      DisplayString
    MAX-ACCESS  read-write
    STATUS      current
    DESCRIPTION
	"The second output name of slave8"
    ::= { slave8OutputCurrentValue 30}
	
slave8OutputCurrentValueThirtyone OBJECT-TYPE
    SYNTAX      DisplayString
    MAX-ACCESS  read-write
    STATUS      current
    DESCRIPTION
	"The second output name of slave8"
    ::= { slave8OutputCurrentValue 31}
	
slave8OutputCurrentValueThirtytwo OBJECT-TYPE
    SYNTAX      DisplayString
    MAX-ACCESS  read-write
    STATUS      current
    DESCRIPTION
	"The second output name of slave8"
    ::= { slave8OutputCurrentValue 32}
	
slave8OutputCurrentValueThirtythree OBJECT-TYPE
    SYNTAX      DisplayString
    MAX-ACCESS  read-write
    STATUS      current
    DESCRIPTION
	"The second output name of slave8"
    ::= { slave8OutputCurrentValue 33}
	
slave8OutputCurrentValueThirtyfour OBJECT-TYPE
    SYNTAX      DisplayString
    MAX-ACCESS  read-write
    STATUS      current
    DESCRIPTION
	"The second output name of slave8"
    ::= { slave8OutputCurrentValue 34}
	
slave8OutputCurrentValueThirtyfive OBJECT-TYPE
    SYNTAX      DisplayString
    MAX-ACCESS  read-write
    STATUS      current
    DESCRIPTION
	"The second output name of slave8"
    ::= { slave8OutputCurrentValue 35}
	
slave8OutputCurrentValueThirtysix OBJECT-TYPE
    SYNTAX      DisplayString
    MAX-ACCESS  read-write
    STATUS      current
    DESCRIPTION
	"The second output name of slave8"
    ::= { slave8OutputCurrentValue 36}
	
slave8OutputCurrentValueThirtyseven OBJECT-TYPE
    SYNTAX      DisplayString
    MAX-ACCESS  read-write
    STATUS      current
    DESCRIPTION
	"The second output name of slave8"
    ::= { slave8OutputCurrentValue 37}
	
slave8OutputCurrentValueThirtyeight OBJECT-TYPE
    SYNTAX      DisplayString
    MAX-ACCESS  read-write
    STATUS      current
    DESCRIPTION
	"The second output name of slave8"
    ::= { slave8OutputCurrentValue 38}
	
slave8OutputCurrentValueThirtynine OBJECT-TYPE
    SYNTAX      DisplayString
    MAX-ACCESS  read-write
    STATUS      current
    DESCRIPTION
	"The second output name of slave8"
    ::= { slave8OutputCurrentValue 39}
	
slave8OutputCurrentValueFourty OBJECT-TYPE
    SYNTAX      DisplayString
    MAX-ACCESS  read-write
    STATUS      current
    DESCRIPTION
	"The second output name of slave8"
    ::= { slave8OutputCurrentValue 40}
	
slave8OutputCurrentValueFourtyone OBJECT-TYPE
    SYNTAX      DisplayString
    MAX-ACCESS  read-write
    STATUS      current
    DESCRIPTION
	"The second output name of slave8"
    ::= { slave8OutputCurrentValue 41}
	
slave8OutputCurrentValueFourtytwo OBJECT-TYPE
    SYNTAX      DisplayString
    MAX-ACCESS  read-write
    STATUS      current
    DESCRIPTION
	"The second output name of slave8"
    ::= { slave8OutputCurrentValue 42}


-------------------------------slave8 output current Min------------------------			
slave8OutputCurrentMin OBJECT IDENTIFIER ::= { slave8OutputCurrent 2}	

slave8OutputCurrentMinOne OBJECT-TYPE
    SYNTAX      DisplayString
    MAX-ACCESS  read-write
    STATUS      current
    DESCRIPTION
	"The first output Min. current alarm value of slave8"
    ::= { slave8OutputCurrentMin 1}

slave8OutputCurrentMinTwo OBJECT-TYPE
    SYNTAX      DisplayString
    MAX-ACCESS  read-write
    STATUS      current
    DESCRIPTION
	"The second output Min. current alarm value of slave8"
    ::= { slave8OutputCurrentMin 2}

slave8OutputCurrentMinThree OBJECT-TYPE
    SYNTAX      DisplayString
    MAX-ACCESS  read-write
    STATUS      current
    DESCRIPTION
	"The second output Min. current alarm value of slave8"
    ::= { slave8OutputCurrentMin 3}

slave8OutputCurrentMinFour OBJECT-TYPE
    SYNTAX      DisplayString
    MAX-ACCESS  read-write
    STATUS      current
    DESCRIPTION
	"The second output Min. current alarm value of slave8"
    ::= { slave8OutputCurrentMin 4}

slave8OutputCurrentMinFive OBJECT-TYPE
    SYNTAX      DisplayString
    MAX-ACCESS  read-write
    STATUS      current
    DESCRIPTION
	"The second output Min. current alarm value of slave8"
    ::= { slave8OutputCurrentMin 5}

slave8OutputCurrentMinSix OBJECT-TYPE
    SYNTAX      DisplayString
    MAX-ACCESS  read-write
    STATUS      current
    DESCRIPTION
	"The second output Min. current alarm value of slave8"
    ::= { slave8OutputCurrentMin 6}

slave8OutputCurrentMinSeven OBJECT-TYPE
    SYNTAX      DisplayString
    MAX-ACCESS  read-write
    STATUS      current
    DESCRIPTION
	"The second output Min. current alarm value of slave8"
    ::= { slave8OutputCurrentMin 7}

slave8OutputCurrentMinEight OBJECT-TYPE
    SYNTAX      DisplayString
    MAX-ACCESS  read-write
    STATUS      current
    DESCRIPTION
	"The second output Min. current alarm value of slave8"
    ::= { slave8OutputCurrentMin 8}

slave8OutputCurrentMinNine OBJECT-TYPE
    SYNTAX      DisplayString
    MAX-ACCESS  read-write
    STATUS      current
    DESCRIPTION
	"The second output Min. current alarm value of slave8"
    ::= { slave8OutputCurrentMin 9}

slave8OutputCurrentMinTen OBJECT-TYPE
    SYNTAX      DisplayString
    MAX-ACCESS  read-write
    STATUS      current
    DESCRIPTION
	"The second output Min. current alarm value of slave8"
    ::= { slave8OutputCurrentMin 10}

slave8OutputCurrentMinEleven OBJECT-TYPE
    SYNTAX      DisplayString
    MAX-ACCESS  read-write
    STATUS      current
    DESCRIPTION
	"The second output Min. current alarm value of slave8"
    ::= { slave8OutputCurrentMin 11}

slave8OutputCurrentMinTwel OBJECT-TYPE
    SYNTAX      DisplayString
    MAX-ACCESS  read-write
    STATUS      current
    DESCRIPTION
	"The second output Min. current alarm value of slave8"
    ::= { slave8OutputCurrentMin 12}

slave8OutputCurrentMinThirteen OBJECT-TYPE
    SYNTAX      DisplayString
    MAX-ACCESS  read-write
    STATUS      current
    DESCRIPTION
	"The second output Min. current alarm value of slave8"
    ::= { slave8OutputCurrentMin 13}

slave8OutputCurrentMinFourteen OBJECT-TYPE
    SYNTAX      DisplayString
    MAX-ACCESS  read-write
    STATUS      current
    DESCRIPTION
	"The second output Min. current alarm value of slave8"
    ::= { slave8OutputCurrentMin 14}

slave8OutputCurrentMinFifteen OBJECT-TYPE
    SYNTAX      DisplayString
    MAX-ACCESS  read-write
    STATUS      current
    DESCRIPTION
	"The second output Min. current alarm value of slave8"
    ::= { slave8OutputCurrentMin 15}

slave8OutputCurrentMinSixteen OBJECT-TYPE
    SYNTAX      DisplayString
    MAX-ACCESS  read-write
    STATUS      current
    DESCRIPTION
	"The second output Min. current alarm value of slave8"
    ::= { slave8OutputCurrentMin 16}

slave8OutputCurrentMinSeventeen OBJECT-TYPE
    SYNTAX      DisplayString
    MAX-ACCESS  read-write
    STATUS      current
    DESCRIPTION
	"The second output Min. current alarm value of slave8"
    ::= { slave8OutputCurrentMin 17}

slave8OutputCurrentMinEighteen OBJECT-TYPE
    SYNTAX      DisplayString
    MAX-ACCESS  read-write
    STATUS      current
    DESCRIPTION
	"The second output Min. current alarm value of slave8"
    ::= { slave8OutputCurrentMin 18}
	
slave8OutputCurrentMinNineteen OBJECT-TYPE
    SYNTAX      DisplayString
    MAX-ACCESS  read-write
    STATUS      current
    DESCRIPTION
	"The second output Min. current alarm value of slave8"
    ::= { slave8OutputCurrentMin 19}
	
slave8OutputCurrentMintwenty OBJECT-TYPE
    SYNTAX      DisplayString
    MAX-ACCESS  read-write
    STATUS      current
    DESCRIPTION
	"The second output Min. current alarm value of slave8"
    ::= { slave8OutputCurrentMin 20}
	
slave8OutputCurrentMinTwentyone OBJECT-TYPE
    SYNTAX      DisplayString
    MAX-ACCESS  read-write
    STATUS      current
    DESCRIPTION
	"The second output Min. current alarm value of slave8"
    ::= { slave8OutputCurrentMin 21}
	
slave8OutputCurrentMinTwentyonetwo OBJECT-TYPE
    SYNTAX      DisplayString
    MAX-ACCESS  read-write
    STATUS      current
    DESCRIPTION
	"The second output Min. current alarm value of slave8"
    ::= { slave8OutputCurrentMin 22}
	
slave8OutputCurrentMinTwentythree OBJECT-TYPE
    SYNTAX      DisplayString
    MAX-ACCESS  read-write
    STATUS      current
    DESCRIPTION
	"The second output Min. current alarm value of slave8"
    ::= { slave8OutputCurrentMin 23}
	
slave8OutputCurrentMinTwentyfour OBJECT-TYPE
    SYNTAX      DisplayString
    MAX-ACCESS  read-write
    STATUS      current
    DESCRIPTION
	"The second output Min. current alarm value of slave8"
    ::= { slave8OutputCurrentMin 24}
	
slave8OutputCurrentMinTwentyfive OBJECT-TYPE
    SYNTAX      DisplayString
    MAX-ACCESS  read-write
    STATUS      current
    DESCRIPTION
	"The second output Min. current alarm value of slave8"
    ::= { slave8OutputCurrentMin 25}
	
slave8OutputCurrentMinTwentysix OBJECT-TYPE
    SYNTAX      DisplayString
    MAX-ACCESS  read-write
    STATUS      current
    DESCRIPTION
	"The second output Min. current alarm value of slave8"
    ::= { slave8OutputCurrentMin 26}
	
slave8OutputCurrentMinTwentyseven OBJECT-TYPE
    SYNTAX      DisplayString
    MAX-ACCESS  read-write
    STATUS      current
    DESCRIPTION
	"The second output Min. current alarm value of slave8"
    ::= { slave8OutputCurrentMin 27}
	
slave8OutputCurrentMinTwentyeight OBJECT-TYPE
    SYNTAX      DisplayString
    MAX-ACCESS  read-write
    STATUS      current
    DESCRIPTION
	"The second output Min. current alarm value of slave8"
    ::= { slave8OutputCurrentMin 28}	
slave8OutputCurrentMinTwentynine OBJECT-TYPE
    SYNTAX      DisplayString
    MAX-ACCESS  read-write
    STATUS      current
    DESCRIPTION
	"The second output Min. current alarm value of slave8"
    ::= { slave8OutputCurrentMin 29}
	
slave8OutputCurrentMinThirty OBJECT-TYPE
    SYNTAX      DisplayString
    MAX-ACCESS  read-write
    STATUS      current
    DESCRIPTION
	"The second output Min. current alarm value of slave8"
    ::= { slave8OutputCurrentMin 30}
	
slave8OutputCurrentMinThirtyone OBJECT-TYPE
    SYNTAX      DisplayString
    MAX-ACCESS  read-write
    STATUS      current
    DESCRIPTION
	"The second output Min. current alarm value of slave8"
    ::= { slave8OutputCurrentMin 31}
	
slave8OutputCurrentMinThirtytwo OBJECT-TYPE
    SYNTAX      DisplayString
    MAX-ACCESS  read-write
    STATUS      current
    DESCRIPTION
	"The second output Min. current alarm value of slave8"
    ::= { slave8OutputCurrentMin 32}
	
slave8OutputCurrentMinThirtythree OBJECT-TYPE
    SYNTAX      DisplayString
    MAX-ACCESS  read-write
    STATUS      current
    DESCRIPTION
	"The second output Min. current alarm value of slave8"
    ::= { slave8OutputCurrentMin 33}
	
slave8OutputCurrentMinThirtyfour OBJECT-TYPE
    SYNTAX      DisplayString
    MAX-ACCESS  read-write
    STATUS      current
    DESCRIPTION
	"The second output Min. current alarm value of slave8"
    ::= { slave8OutputCurrentMin 34}
	
slave8OutputCurrentMinThirtyfive OBJECT-TYPE
    SYNTAX      DisplayString
    MAX-ACCESS  read-write
    STATUS      current
    DESCRIPTION
	"The second output Min. current alarm value of slave8"
    ::= { slave8OutputCurrentMin 35}
	
slave8OutputCurrentMinThirtysix OBJECT-TYPE
    SYNTAX      DisplayString
    MAX-ACCESS  read-write
    STATUS      current
    DESCRIPTION
	"The second output Min. current alarm value of slave8"
    ::= { slave8OutputCurrentMin 36}
	
slave8OutputCurrentMinThirtyseven OBJECT-TYPE
    SYNTAX      DisplayString
    MAX-ACCESS  read-write
    STATUS      current
    DESCRIPTION
	"The second output Min. current alarm value of slave8"
    ::= { slave8OutputCurrentMin 37}
	
slave8OutputCurrentMinThirtyeight OBJECT-TYPE
    SYNTAX      DisplayString
    MAX-ACCESS  read-write
    STATUS      current
    DESCRIPTION
	"The second output Min. current alarm value of slave8"
    ::= { slave8OutputCurrentMin 38}
	
slave8OutputCurrentMinThirtynine OBJECT-TYPE
    SYNTAX      DisplayString
    MAX-ACCESS  read-write
    STATUS      current
    DESCRIPTION
	"The second output Min. current alarm value of slave8"
    ::= { slave8OutputCurrentMin 39}
	
slave8OutputCurrentMinFourty OBJECT-TYPE
    SYNTAX      DisplayString
    MAX-ACCESS  read-write
    STATUS      current
    DESCRIPTION
	"The second output Min. current alarm value of slave8"
    ::= { slave8OutputCurrentMin 40}
	
slave8OutputCurrentMinFourtyone OBJECT-TYPE
    SYNTAX      DisplayString
    MAX-ACCESS  read-write
    STATUS      current
    DESCRIPTION
	"The second output Min. current alarm value of slave8"
    ::= { slave8OutputCurrentMin 41}
	
slave8OutputCurrentMinFourtytwo OBJECT-TYPE
    SYNTAX      DisplayString
    MAX-ACCESS  read-write
    STATUS      current
    DESCRIPTION
	"The second output Min. current alarm value of slave8"
    ::= { slave8OutputCurrentMin 42}


------------------------slave8 output current Min critical----------------			
slave8OutputCurrentMinCritical OBJECT IDENTIFIER ::= { slave8OutputCurrent 3}	

slave8OutputCurrentMinCriticalOne OBJECT-TYPE
    SYNTAX      DisplayString
    MAX-ACCESS  read-write
    STATUS      current
    DESCRIPTION
	"The first output Min. current warning value of slave8"
    ::= { slave8OutputCurrentMinCritical 1}

slave8OutputCurrentMinCriticalTwo OBJECT-TYPE
    SYNTAX      DisplayString
    MAX-ACCESS  read-write
    STATUS      current
    DESCRIPTION
	"The second output Min. current warning value of slave8"
    ::= { slave8OutputCurrentMinCritical 2}

slave8OutputCurrentMinCriticalThree OBJECT-TYPE
    SYNTAX      DisplayString
    MAX-ACCESS  read-write
    STATUS      current
    DESCRIPTION
	"The second output Min. current warning value of slave8"
    ::= { slave8OutputCurrentMinCritical 3}

slave8OutputCurrentMinCriticalFour OBJECT-TYPE
    SYNTAX      DisplayString
    MAX-ACCESS  read-write
    STATUS      current
    DESCRIPTION
	"The second output Min. current warning value of slave8"
    ::= { slave8OutputCurrentMinCritical 4}

slave8OutputCurrentMinCriticalFive OBJECT-TYPE
    SYNTAX      DisplayString
    MAX-ACCESS  read-write
    STATUS      current
    DESCRIPTION
	"The second output Min. current warning value of slave8"
    ::= { slave8OutputCurrentMinCritical 5}

slave8OutputCurrentMinCriticalSix OBJECT-TYPE
    SYNTAX      DisplayString
    MAX-ACCESS  read-write
    STATUS      current
    DESCRIPTION
	"The second output Min. current warning value of slave8"
    ::= { slave8OutputCurrentMinCritical 6}

slave8OutputCurrentMinCriticalSeven OBJECT-TYPE
    SYNTAX      DisplayString
    MAX-ACCESS  read-write
    STATUS      current
    DESCRIPTION
	"The second output Min. current warning value of slave8"
    ::= { slave8OutputCurrentMinCritical 7}

slave8OutputCurrentMinCriticalEight OBJECT-TYPE
    SYNTAX      DisplayString
    MAX-ACCESS  read-write
    STATUS      current
    DESCRIPTION
	"The second output Min. current warning value of slave8"
    ::= { slave8OutputCurrentMinCritical 8}

slave8OutputCurrentMinCriticalNine OBJECT-TYPE
    SYNTAX      DisplayString
    MAX-ACCESS  read-write
    STATUS      current
    DESCRIPTION
	"The second output Min. current warning value of slave8"
    ::= { slave8OutputCurrentMinCritical 9}

slave8OutputCurrentMinCriticalTen OBJECT-TYPE
    SYNTAX      DisplayString
    MAX-ACCESS  read-write
    STATUS      current
    DESCRIPTION
	"The second output Min. current warning value of slave8"
    ::= { slave8OutputCurrentMinCritical 10}

slave8OutputCurrentMinCriticalEleven OBJECT-TYPE
    SYNTAX      DisplayString
    MAX-ACCESS  read-write
    STATUS      current
    DESCRIPTION
	"The second output Min. current warning value of slave8"
    ::= { slave8OutputCurrentMinCritical 11}

slave8OutputCurrentMinCriticalTwel OBJECT-TYPE
    SYNTAX      DisplayString
    MAX-ACCESS  read-write
    STATUS      current
    DESCRIPTION
	"The second output Min. current warning value of slave8"
    ::= { slave8OutputCurrentMinCritical 12}

slave8OutputCurrentMinCriticalThirteen OBJECT-TYPE
    SYNTAX      DisplayString
    MAX-ACCESS  read-write
    STATUS      current
    DESCRIPTION
	"The second output Min. current warning value of slave8"
    ::= { slave8OutputCurrentMinCritical 13}

slave8OutputCurrentMinCriticalFourteen OBJECT-TYPE
    SYNTAX      DisplayString
    MAX-ACCESS  read-write
    STATUS      current
    DESCRIPTION
	"The second output Min. current warning value of slave8"
    ::= { slave8OutputCurrentMinCritical 14}

slave8OutputCurrentMinCriticalFifteen OBJECT-TYPE
    SYNTAX      DisplayString
    MAX-ACCESS  read-write
    STATUS      current
    DESCRIPTION
	"The second output Min. current warning value of slave8"
    ::= { slave8OutputCurrentMinCritical 15}

slave8OutputCurrentMinCriticalSixteen OBJECT-TYPE
    SYNTAX      DisplayString
    MAX-ACCESS  read-write
    STATUS      current
    DESCRIPTION
	"The second output Min. current warning value of slave8"
    ::= { slave8OutputCurrentMinCritical 16}

slave8OutputCurrentMinCriticalSeventeen OBJECT-TYPE
    SYNTAX      DisplayString
    MAX-ACCESS  read-write
    STATUS      current
    DESCRIPTION
	"The second output Min. current warning value of slave8"
    ::= { slave8OutputCurrentMinCritical 17}

slave8OutputCurrentMinCriticalEighteen OBJECT-TYPE
    SYNTAX      DisplayString
    MAX-ACCESS  read-write
    STATUS      current
    DESCRIPTION
	"The second output Min. current warning value of slave8"
    ::= { slave8OutputCurrentMinCritical 18}
	
slave8OutputCurrentMinCriticalNineteen OBJECT-TYPE
    SYNTAX      DisplayString
    MAX-ACCESS  read-write
    STATUS      current
    DESCRIPTION
	"The second output Min. current warning value of slave8"
    ::= { slave8OutputCurrentMinCritical 19}
	
slave8OutputCurrentMinCriticaltwenty OBJECT-TYPE
    SYNTAX      DisplayString
    MAX-ACCESS  read-write
    STATUS      current
    DESCRIPTION
	"The second output Min. current warning value of slave8"
    ::= { slave8OutputCurrentMinCritical 20}
	
slave8OutputCurrentMinCriticalTwentyone OBJECT-TYPE
    SYNTAX      DisplayString
    MAX-ACCESS  read-write
    STATUS      current
    DESCRIPTION
	"The second output Min. current warning value of slave8"
    ::= { slave8OutputCurrentMinCritical 21}
	
slave8OutputCurrentMinCriticalTwentyonetwo OBJECT-TYPE
    SYNTAX      DisplayString
    MAX-ACCESS  read-write
    STATUS      current
    DESCRIPTION
	"The second output Min. current warning value of slave8"
    ::= { slave8OutputCurrentMinCritical 22}
	
slave8OutputCurrentMinCriticalTwentythree OBJECT-TYPE
    SYNTAX      DisplayString
    MAX-ACCESS  read-write
    STATUS      current
    DESCRIPTION
	"The second output Min. current warning value of slave8"
    ::= { slave8OutputCurrentMinCritical 23}
	
slave8OutputCurrentMinCriticalTwentyfour OBJECT-TYPE
    SYNTAX      DisplayString
    MAX-ACCESS  read-write
    STATUS      current
    DESCRIPTION
	"The second output Min. current warning value of slave8"
    ::= { slave8OutputCurrentMinCritical 24}
	
slave8OutputCurrentMinCriticalTwentyfive OBJECT-TYPE
    SYNTAX      DisplayString
    MAX-ACCESS  read-write
    STATUS      current
    DESCRIPTION
	"The second output Min. current warning value of slave8"
    ::= { slave8OutputCurrentMinCritical 25}
	
slave8OutputCurrentMinCriticalTwentysix OBJECT-TYPE
    SYNTAX      DisplayString
    MAX-ACCESS  read-write
    STATUS      current
    DESCRIPTION
	"The second output Min. current warning value of slave8"
    ::= { slave8OutputCurrentMinCritical 26}
	
slave8OutputCurrentMinCriticalTwentyseven OBJECT-TYPE
    SYNTAX      DisplayString
    MAX-ACCESS  read-write
    STATUS      current
    DESCRIPTION
	"The second output Min. current warning value of slave8"
    ::= { slave8OutputCurrentMinCritical 27}
	
slave8OutputCurrentMinCriticalTwentyeight OBJECT-TYPE
    SYNTAX      DisplayString
    MAX-ACCESS  read-write
    STATUS      current
    DESCRIPTION
	"The second output Min. current warning value of slave8"
    ::= { slave8OutputCurrentMinCritical 28}	
slave8OutputCurrentMinCriticalTwentynine OBJECT-TYPE
    SYNTAX      DisplayString
    MAX-ACCESS  read-write
    STATUS      current
    DESCRIPTION
	"The second output Min. current warning value of slave8"
    ::= { slave8OutputCurrentMinCritical 29}
	
slave8OutputCurrentMinCriticalThirty OBJECT-TYPE
    SYNTAX      DisplayString
    MAX-ACCESS  read-write
    STATUS      current
    DESCRIPTION
	"The second output Min. current warning value of slave8"
    ::= { slave8OutputCurrentMinCritical 30}
	
slave8OutputCurrentMinCriticalThirtyone OBJECT-TYPE
    SYNTAX      DisplayString
    MAX-ACCESS  read-write
    STATUS      current
    DESCRIPTION
	"The second output Min. current warning value of slave8"
    ::= { slave8OutputCurrentMinCritical 31}
	
slave8OutputCurrentMinCriticalThirtytwo OBJECT-TYPE
    SYNTAX      DisplayString
    MAX-ACCESS  read-write
    STATUS      current
    DESCRIPTION
	"The second output Min. current warning value of slave8"
    ::= { slave8OutputCurrentMinCritical 32}
	
slave8OutputCurrentMinCriticalThirtythree OBJECT-TYPE
    SYNTAX      DisplayString
    MAX-ACCESS  read-write
    STATUS      current
    DESCRIPTION
	"The second output Min. current warning value of slave8"
    ::= { slave8OutputCurrentMinCritical 33}
	
slave8OutputCurrentMinCriticalThirtyfour OBJECT-TYPE
    SYNTAX      DisplayString
    MAX-ACCESS  read-write
    STATUS      current
    DESCRIPTION
	"The second output Min. current warning value of slave8"
    ::= { slave8OutputCurrentMinCritical 34}
	
slave8OutputCurrentMinCriticalThirtyfive OBJECT-TYPE
    SYNTAX      DisplayString
    MAX-ACCESS  read-write
    STATUS      current
    DESCRIPTION
	"The second output Min. current warning value of slave8"
    ::= { slave8OutputCurrentMinCritical 35}
	
slave8OutputCurrentMinCriticalThirtysix OBJECT-TYPE
    SYNTAX      DisplayString
    MAX-ACCESS  read-write
    STATUS      current
    DESCRIPTION
	"The second output Min. current warning value of slave8"
    ::= { slave8OutputCurrentMinCritical 36}
	
slave8OutputCurrentMinCriticalThirtyseven OBJECT-TYPE
    SYNTAX      DisplayString
    MAX-ACCESS  read-write
    STATUS      current
    DESCRIPTION
	"The second output Min. current warning value of slave8"
    ::= { slave8OutputCurrentMinCritical 37}
	
slave8OutputCurrentMinCriticalThirtyeight OBJECT-TYPE
    SYNTAX      DisplayString
    MAX-ACCESS  read-write
    STATUS      current
    DESCRIPTION
	"The second output Min. current warning value of slave8"
    ::= { slave8OutputCurrentMinCritical 38}
	
slave8OutputCurrentMinCriticalThirtynine OBJECT-TYPE
    SYNTAX      DisplayString
    MAX-ACCESS  read-write
    STATUS      current
    DESCRIPTION
	"The second output Min. current warning value of slave8"
    ::= { slave8OutputCurrentMinCritical 39}
	
slave8OutputCurrentMinCriticalFourty OBJECT-TYPE
    SYNTAX      DisplayString
    MAX-ACCESS  read-write
    STATUS      current
    DESCRIPTION
	"The second output Min. current warning value of slave8"
    ::= { slave8OutputCurrentMinCritical 40}
	
slave8OutputCurrentMinCriticalFourtyone OBJECT-TYPE
    SYNTAX      DisplayString
    MAX-ACCESS  read-write
    STATUS      current
    DESCRIPTION
	"The second output Min. current warning value of slave8"
    ::= { slave8OutputCurrentMinCritical 41}
	
slave8OutputCurrentMinCriticalFourtytwo OBJECT-TYPE
    SYNTAX      DisplayString
    MAX-ACCESS  read-write
    STATUS      current
    DESCRIPTION
	"The second output Min. current warning value of slave8"
    ::= { slave8OutputCurrentMinCritical 42}
	
	
------------------------slave8 output current Max critical----------------			
slave8OutputCurrentMaxCritical OBJECT IDENTIFIER ::= { slave8OutputCurrent 4}	

slave8OutputCurrentMaxCriticalOne OBJECT-TYPE
    SYNTAX      DisplayString
    MAX-ACCESS  read-write
    STATUS      current
    DESCRIPTION
	"The first output Max. current warning value of slave8"
    ::= { slave8OutputCurrentMaxCritical 1}

slave8OutputCurrentMaxCriticalTwo OBJECT-TYPE
    SYNTAX      DisplayString
    MAX-ACCESS  read-write
    STATUS      current
    DESCRIPTION
	"The second output Max. current warning value of slave8"
    ::= { slave8OutputCurrentMaxCritical 2}

slave8OutputCurrentMaxCriticalThree OBJECT-TYPE
    SYNTAX      DisplayString
    MAX-ACCESS  read-write
    STATUS      current
    DESCRIPTION
	"The second output Max. current warning value of slave8"
    ::= { slave8OutputCurrentMaxCritical 3}

slave8OutputCurrentMaxCriticalFour OBJECT-TYPE
    SYNTAX      DisplayString
    MAX-ACCESS  read-write
    STATUS      current
    DESCRIPTION
	"The second output Max. current warning value of slave8"
    ::= { slave8OutputCurrentMaxCritical 4}

slave8OutputCurrentMaxCriticalFive OBJECT-TYPE
    SYNTAX      DisplayString
    MAX-ACCESS  read-write
    STATUS      current
    DESCRIPTION
	"The second output Max. current warning value of slave8"
    ::= { slave8OutputCurrentMaxCritical 5}

slave8OutputCurrentMaxCriticalSix OBJECT-TYPE
    SYNTAX      DisplayString
    MAX-ACCESS  read-write
    STATUS      current
    DESCRIPTION
	"The second output Max. current warning value of slave8"
    ::= { slave8OutputCurrentMaxCritical 6}

slave8OutputCurrentMaxCriticalSeven OBJECT-TYPE
    SYNTAX      DisplayString
    MAX-ACCESS  read-write
    STATUS      current
    DESCRIPTION
	"The second output Max. current warning value of slave8"
    ::= { slave8OutputCurrentMaxCritical 7}

slave8OutputCurrentMaxCriticalEight OBJECT-TYPE
    SYNTAX      DisplayString
    MAX-ACCESS  read-write
    STATUS      current
    DESCRIPTION
	"The second output Max. current warning value of slave8"
    ::= { slave8OutputCurrentMaxCritical 8}

slave8OutputCurrentMaxCriticalNine OBJECT-TYPE
    SYNTAX      DisplayString
    MAX-ACCESS  read-write
    STATUS      current
    DESCRIPTION
	"The second output Max. current warning value of slave8"
    ::= { slave8OutputCurrentMaxCritical 9}

slave8OutputCurrentMaxCriticalTen OBJECT-TYPE
    SYNTAX      DisplayString
    MAX-ACCESS  read-write
    STATUS      current
    DESCRIPTION
	"The second output Max. current warning value of slave8"
    ::= { slave8OutputCurrentMaxCritical 10}

slave8OutputCurrentMaxCriticalEleven OBJECT-TYPE
    SYNTAX      DisplayString
    MAX-ACCESS  read-write
    STATUS      current
    DESCRIPTION
	"The second output Max. current warning value of slave8"
    ::= { slave8OutputCurrentMaxCritical 11}

slave8OutputCurrentMaxCriticalTwel OBJECT-TYPE
    SYNTAX      DisplayString
    MAX-ACCESS  read-write
    STATUS      current
    DESCRIPTION
	"The second output Max. current warning value of slave8"
    ::= { slave8OutputCurrentMaxCritical 12}

slave8OutputCurrentMaxCriticalThirteen OBJECT-TYPE
    SYNTAX      DisplayString
    MAX-ACCESS  read-write
    STATUS      current
    DESCRIPTION
	"The second output Max. current warning value of slave8"
    ::= { slave8OutputCurrentMaxCritical 13}

slave8OutputCurrentMaxCriticalFourteen OBJECT-TYPE
    SYNTAX      DisplayString
    MAX-ACCESS  read-write
    STATUS      current
    DESCRIPTION
	"The second output Max. current warning value of slave8"
    ::= { slave8OutputCurrentMaxCritical 14}

slave8OutputCurrentMaxCriticalFifteen OBJECT-TYPE
    SYNTAX      DisplayString
    MAX-ACCESS  read-write
    STATUS      current
    DESCRIPTION
	"The second output Max. current warning value of slave8"
    ::= { slave8OutputCurrentMaxCritical 15}

slave8OutputCurrentMaxCriticalSixteen OBJECT-TYPE
    SYNTAX      DisplayString
    MAX-ACCESS  read-write
    STATUS      current
    DESCRIPTION
	"The second output Max. current warning value of slave8"
    ::= { slave8OutputCurrentMaxCritical 16}

slave8OutputCurrentMaxCriticalSeventeen OBJECT-TYPE
    SYNTAX      DisplayString
    MAX-ACCESS  read-write
    STATUS      current
    DESCRIPTION
	"The second output Max. current warning value of slave8"
    ::= { slave8OutputCurrentMaxCritical 17}

slave8OutputCurrentMaxCriticalEighteen OBJECT-TYPE
    SYNTAX      DisplayString
    MAX-ACCESS  read-write
    STATUS      current
    DESCRIPTION
	"The second output Max. current warning value of slave8"
    ::= { slave8OutputCurrentMaxCritical 18}
	
slave8OutputCurrentMaxCriticalNineteen OBJECT-TYPE
    SYNTAX      DisplayString
    MAX-ACCESS  read-write
    STATUS      current
    DESCRIPTION
	"The second output Max. current warning value of slave8"
    ::= { slave8OutputCurrentMaxCritical 19}
	
slave8OutputCurrentMaxCriticaltwenty OBJECT-TYPE
    SYNTAX      DisplayString
    MAX-ACCESS  read-write
    STATUS      current
    DESCRIPTION
	"The second output Max. current warning value of slave8"
    ::= { slave8OutputCurrentMaxCritical 20}
	
slave8OutputCurrentMaxCriticalTwentyone OBJECT-TYPE
    SYNTAX      DisplayString
    MAX-ACCESS  read-write
    STATUS      current
    DESCRIPTION
	"The second output Max. current warning value of slave8"
    ::= { slave8OutputCurrentMaxCritical 21}
	
slave8OutputCurrentMaxCriticalTwentyonetwo OBJECT-TYPE
    SYNTAX      DisplayString
    MAX-ACCESS  read-write
    STATUS      current
    DESCRIPTION
	"The second output Max. current warning value of slave8"
    ::= { slave8OutputCurrentMaxCritical 22}
	
slave8OutputCurrentMaxCriticalTwentythree OBJECT-TYPE
    SYNTAX      DisplayString
    MAX-ACCESS  read-write
    STATUS      current
    DESCRIPTION
	"The second output Max. current warning value of slave8"
    ::= { slave8OutputCurrentMaxCritical 23}
	
slave8OutputCurrentMaxCriticalTwentyfour OBJECT-TYPE
    SYNTAX      DisplayString
    MAX-ACCESS  read-write
    STATUS      current
    DESCRIPTION
	"The second output Max. current warning value of slave8"
    ::= { slave8OutputCurrentMaxCritical 24}
	
slave8OutputCurrentMaxCriticalTwentyfive OBJECT-TYPE
    SYNTAX      DisplayString
    MAX-ACCESS  read-write
    STATUS      current
    DESCRIPTION
	"The second output Max. current warning value of slave8"
    ::= { slave8OutputCurrentMaxCritical 25}
	
slave8OutputCurrentMaxCriticalTwentysix OBJECT-TYPE
    SYNTAX      DisplayString
    MAX-ACCESS  read-write
    STATUS      current
    DESCRIPTION
	"The second output Max. current warning value of slave8"
    ::= { slave8OutputCurrentMaxCritical 26}
	
slave8OutputCurrentMaxCriticalTwentyseven OBJECT-TYPE
    SYNTAX      DisplayString
    MAX-ACCESS  read-write
    STATUS      current
    DESCRIPTION
	"The second output Max. current warning value of slave8"
    ::= { slave8OutputCurrentMaxCritical 27}
	
slave8OutputCurrentMaxCriticalTwentyeight OBJECT-TYPE
    SYNTAX      DisplayString
    MAX-ACCESS  read-write
    STATUS      current
    DESCRIPTION
	"The second output Max. current warning value of slave8"
    ::= { slave8OutputCurrentMaxCritical 28}	
slave8OutputCurrentMaxCriticalTwentynine OBJECT-TYPE
    SYNTAX      DisplayString
    MAX-ACCESS  read-write
    STATUS      current
    DESCRIPTION
	"The second output Max. current warning value of slave8"
    ::= { slave8OutputCurrentMaxCritical 29}
	
slave8OutputCurrentMaxCriticalThirty OBJECT-TYPE
    SYNTAX      DisplayString
    MAX-ACCESS  read-write
    STATUS      current
    DESCRIPTION
	"The second output Max. current warning value of slave8"
    ::= { slave8OutputCurrentMaxCritical 30}
	
slave8OutputCurrentMaxCriticalThirtyone OBJECT-TYPE
    SYNTAX      DisplayString
    MAX-ACCESS  read-write
    STATUS      current
    DESCRIPTION
	"The second output Max. current warning value of slave8"
    ::= { slave8OutputCurrentMaxCritical 31}
	
slave8OutputCurrentMaxCriticalThirtytwo OBJECT-TYPE
    SYNTAX      DisplayString
    MAX-ACCESS  read-write
    STATUS      current
    DESCRIPTION
	"The second output Max. current warning value of slave8"
    ::= { slave8OutputCurrentMaxCritical 32}
	
slave8OutputCurrentMaxCriticalThirtythree OBJECT-TYPE
    SYNTAX      DisplayString
    MAX-ACCESS  read-write
    STATUS      current
    DESCRIPTION
	"The second output Max. current warning value of slave8"
    ::= { slave8OutputCurrentMaxCritical 33}
	
slave8OutputCurrentMaxCriticalThirtyfour OBJECT-TYPE
    SYNTAX      DisplayString
    MAX-ACCESS  read-write
    STATUS      current
    DESCRIPTION
	"The second output Max. current warning value of slave8"
    ::= { slave8OutputCurrentMaxCritical 34}
	
slave8OutputCurrentMaxCriticalThirtyfive OBJECT-TYPE
    SYNTAX      DisplayString
    MAX-ACCESS  read-write
    STATUS      current
    DESCRIPTION
	"The second output Max. current warning value of slave8"
    ::= { slave8OutputCurrentMaxCritical 35}
	
slave8OutputCurrentMaxCriticalThirtysix OBJECT-TYPE
    SYNTAX      DisplayString
    MAX-ACCESS  read-write
    STATUS      current
    DESCRIPTION
	"The second output Max. current warning value of slave8"
    ::= { slave8OutputCurrentMaxCritical 36}
	
slave8OutputCurrentMaxCriticalThirtyseven OBJECT-TYPE
    SYNTAX      DisplayString
    MAX-ACCESS  read-write
    STATUS      current
    DESCRIPTION
	"The second output Max. current warning value of slave8"
    ::= { slave8OutputCurrentMaxCritical 37}
	
slave8OutputCurrentMaxCriticalThirtyeight OBJECT-TYPE
    SYNTAX      DisplayString
    MAX-ACCESS  read-write
    STATUS      current
    DESCRIPTION
	"The second output Max. current warning value of slave8"
    ::= { slave8OutputCurrentMaxCritical 38}
	
slave8OutputCurrentMaxCriticalThirtynine OBJECT-TYPE
    SYNTAX      DisplayString
    MAX-ACCESS  read-write
    STATUS      current
    DESCRIPTION
	"The second output Max. current warning value of slave8"
    ::= { slave8OutputCurrentMaxCritical 39}
	
slave8OutputCurrentMaxCriticalFourty OBJECT-TYPE
    SYNTAX      DisplayString
    MAX-ACCESS  read-write
    STATUS      current
    DESCRIPTION
	"The second output Max. current warning value of slave8"
    ::= { slave8OutputCurrentMaxCritical 40}
	
slave8OutputCurrentMaxCriticalFourtyone OBJECT-TYPE
    SYNTAX      DisplayString
    MAX-ACCESS  read-write
    STATUS      current
    DESCRIPTION
	"The second output Max. current warning value of slave8"
    ::= { slave8OutputCurrentMaxCritical 41}
	
slave8OutputCurrentMaxCriticalFourtytwo OBJECT-TYPE
    SYNTAX      DisplayString
    MAX-ACCESS  read-write
    STATUS      current
    DESCRIPTION
	"The second output Max. current warning value of slave8"
    ::= { slave8OutputCurrentMaxCritical 42}
	
	
------------------------slave8 output current Max----------------			
slave8OutputCurrentMax OBJECT IDENTIFIER ::= { slave8OutputCurrent 5}
	
slave8OutputCurrentMaxOne OBJECT-TYPE
    SYNTAX      DisplayString
    MAX-ACCESS  read-write
    STATUS      current
    DESCRIPTION
	"The first output Max. current alarm value of slave8"
    ::= { slave8OutputCurrentMax 1}

slave8OutputCurrentMaxTwo OBJECT-TYPE
    SYNTAX      DisplayString
    MAX-ACCESS  read-write
    STATUS      current
    DESCRIPTION
	"The second output Max. current alarm value of slave8"
    ::= { slave8OutputCurrentMax 2}

slave8OutputCurrentMaxThree OBJECT-TYPE
    SYNTAX      DisplayString
    MAX-ACCESS  read-write
    STATUS      current
    DESCRIPTION
	"The second output Max. current alarm value of slave8"
    ::= { slave8OutputCurrentMax 3}

slave8OutputCurrentMaxFour OBJECT-TYPE
    SYNTAX      DisplayString
    MAX-ACCESS  read-write
    STATUS      current
    DESCRIPTION
	"The second output Max. current alarm value of slave8"
    ::= { slave8OutputCurrentMax 4}

slave8OutputCurrentMaxFive OBJECT-TYPE
    SYNTAX      DisplayString
    MAX-ACCESS  read-write
    STATUS      current
    DESCRIPTION
	"The second output Max. current alarm value of slave8"
    ::= { slave8OutputCurrentMax 5}

slave8OutputCurrentMaxSix OBJECT-TYPE
    SYNTAX      DisplayString
    MAX-ACCESS  read-write
    STATUS      current
    DESCRIPTION
	"The second output Max. current alarm value of slave8"
    ::= { slave8OutputCurrentMax 6}

slave8OutputCurrentMaxSeven OBJECT-TYPE
    SYNTAX      DisplayString
    MAX-ACCESS  read-write
    STATUS      current
    DESCRIPTION
	"The second output Max. current alarm value of slave8"
    ::= { slave8OutputCurrentMax 7}

slave8OutputCurrentMaxEight OBJECT-TYPE
    SYNTAX      DisplayString
    MAX-ACCESS  read-write
    STATUS      current
    DESCRIPTION
	"The second output Max. current alarm value of slave8"
    ::= { slave8OutputCurrentMax 8}

slave8OutputCurrentMaxNine OBJECT-TYPE
    SYNTAX      DisplayString
    MAX-ACCESS  read-write
    STATUS      current
    DESCRIPTION
	"The second output Max. current alarm value of slave8"
    ::= { slave8OutputCurrentMax 9}

slave8OutputCurrentMaxTen OBJECT-TYPE
    SYNTAX      DisplayString
    MAX-ACCESS  read-write
    STATUS      current
    DESCRIPTION
	"The second output Max. current alarm value of slave8"
    ::= { slave8OutputCurrentMax 10}

slave8OutputCurrentMaxEleven OBJECT-TYPE
    SYNTAX      DisplayString
    MAX-ACCESS  read-write
    STATUS      current
    DESCRIPTION
	"The second output Max. current alarm value of slave8"
    ::= { slave8OutputCurrentMax 11}

slave8OutputCurrentMaxTwel OBJECT-TYPE
    SYNTAX      DisplayString
    MAX-ACCESS  read-write
    STATUS      current
    DESCRIPTION
	"The second output Max. current alarm value of slave8"
    ::= { slave8OutputCurrentMax 12}

slave8OutputCurrentMaxThirteen OBJECT-TYPE
    SYNTAX      DisplayString
    MAX-ACCESS  read-write
    STATUS      current
    DESCRIPTION
	"The second output Max. current alarm value of slave8"
    ::= { slave8OutputCurrentMax 13}

slave8OutputCurrentMaxFourteen OBJECT-TYPE
    SYNTAX      DisplayString
    MAX-ACCESS  read-write
    STATUS      current
    DESCRIPTION
	"The second output Max. current alarm value of slave8"
    ::= { slave8OutputCurrentMax 14}

slave8OutputCurrentMaxFifteen OBJECT-TYPE
    SYNTAX      DisplayString
    MAX-ACCESS  read-write
    STATUS      current
    DESCRIPTION
	"The second output Max. current alarm value of slave8"
    ::= { slave8OutputCurrentMax 15}

slave8OutputCurrentMaxSixteen OBJECT-TYPE
    SYNTAX      DisplayString
    MAX-ACCESS  read-write
    STATUS      current
    DESCRIPTION
	"The second output Max. current alarm value of slave8"
    ::= { slave8OutputCurrentMax 16}

slave8OutputCurrentMaxSeventeen OBJECT-TYPE
    SYNTAX      DisplayString
    MAX-ACCESS  read-write
    STATUS      current
    DESCRIPTION
	"The second output Max. current alarm value of slave8"
    ::= { slave8OutputCurrentMax 17}

slave8OutputCurrentMaxEighteen OBJECT-TYPE
    SYNTAX      DisplayString
    MAX-ACCESS  read-write
    STATUS      current
    DESCRIPTION
	"The second output Max. current alarm value of slave8"
    ::= { slave8OutputCurrentMax 18}
	
slave8OutputCurrentMaxNineteen OBJECT-TYPE
    SYNTAX      DisplayString
    MAX-ACCESS  read-write
    STATUS      current
    DESCRIPTION
	"The second output Max. current alarm value of slave8"
    ::= { slave8OutputCurrentMax 19}
	
slave8OutputCurrentMaxtwenty OBJECT-TYPE
    SYNTAX      DisplayString
    MAX-ACCESS  read-write
    STATUS      current
    DESCRIPTION
	"The second output Max. current alarm value of slave8"
    ::= { slave8OutputCurrentMax 20}
	
slave8OutputCurrentMaxTwentyone OBJECT-TYPE
    SYNTAX      DisplayString
    MAX-ACCESS  read-write
    STATUS      current
    DESCRIPTION
	"The second output Max. current alarm value of slave8"
    ::= { slave8OutputCurrentMax 21}
	
slave8OutputCurrentMaxTwentyonetwo OBJECT-TYPE
    SYNTAX      DisplayString
    MAX-ACCESS  read-write
    STATUS      current
    DESCRIPTION
	"The second output Max. current alarm value of slave8"
    ::= { slave8OutputCurrentMax 22}
	
slave8OutputCurrentMaxTwentythree OBJECT-TYPE
    SYNTAX      DisplayString
    MAX-ACCESS  read-write
    STATUS      current
    DESCRIPTION
	"The second output Max. current alarm value of slave8"
    ::= { slave8OutputCurrentMax 23}
	
slave8OutputCurrentMaxTwentyfour OBJECT-TYPE
    SYNTAX      DisplayString
    MAX-ACCESS  read-write
    STATUS      current
    DESCRIPTION
	"The second output Max. current alarm value of slave8"
    ::= { slave8OutputCurrentMax 24}
	
slave8OutputCurrentMaxTwentyfive OBJECT-TYPE
    SYNTAX      DisplayString
    MAX-ACCESS  read-write
    STATUS      current
    DESCRIPTION
	"The second output Max. current alarm value of slave8"
    ::= { slave8OutputCurrentMax 25}
	
slave8OutputCurrentMaxTwentysix OBJECT-TYPE
    SYNTAX      DisplayString
    MAX-ACCESS  read-write
    STATUS      current
    DESCRIPTION
	"The second output Max. current alarm value of slave8"
    ::= { slave8OutputCurrentMax 26}
	
slave8OutputCurrentMaxTwentyseven OBJECT-TYPE
    SYNTAX      DisplayString
    MAX-ACCESS  read-write
    STATUS      current
    DESCRIPTION
	"The second output Max. current alarm value of slave8"
    ::= { slave8OutputCurrentMax 27}
	
slave8OutputCurrentMaxTwentyeight OBJECT-TYPE
    SYNTAX      DisplayString
    MAX-ACCESS  read-write
    STATUS      current
    DESCRIPTION
	"The second output Max. current alarm value of slave8"
    ::= { slave8OutputCurrentMax 28}	
slave8OutputCurrentMaxTwentynine OBJECT-TYPE
    SYNTAX      DisplayString
    MAX-ACCESS  read-write
    STATUS      current
    DESCRIPTION
	"The second output Max. current alarm value of slave8"
    ::= { slave8OutputCurrentMax 29}
	
slave8OutputCurrentMaxThirty OBJECT-TYPE
    SYNTAX      DisplayString
    MAX-ACCESS  read-write
    STATUS      current
    DESCRIPTION
	"The second output Max. current alarm value of slave8"
    ::= { slave8OutputCurrentMax 30}
	
slave8OutputCurrentMaxThirtyone OBJECT-TYPE
    SYNTAX      DisplayString
    MAX-ACCESS  read-write
    STATUS      current
    DESCRIPTION
	"The second output Max. current alarm value of slave8"
    ::= { slave8OutputCurrentMax 31}
	
slave8OutputCurrentMaxThirtytwo OBJECT-TYPE
    SYNTAX      DisplayString
    MAX-ACCESS  read-write
    STATUS      current
    DESCRIPTION
	"The second output Max. current alarm value of slave8"
    ::= { slave8OutputCurrentMax 32}
	
slave8OutputCurrentMaxThirtythree OBJECT-TYPE
    SYNTAX      DisplayString
    MAX-ACCESS  read-write
    STATUS      current
    DESCRIPTION
	"The second output Max. current alarm value of slave8"
    ::= { slave8OutputCurrentMax 33}
	
slave8OutputCurrentMaxThirtyfour OBJECT-TYPE
    SYNTAX      DisplayString
    MAX-ACCESS  read-write
    STATUS      current
    DESCRIPTION
	"The second output Max. current alarm value of slave8"
    ::= { slave8OutputCurrentMax 34}
	
slave8OutputCurrentMaxThirtyfive OBJECT-TYPE
    SYNTAX      DisplayString
    MAX-ACCESS  read-write
    STATUS      current
    DESCRIPTION
	"The second output Max. current alarm value of slave8"
    ::= { slave8OutputCurrentMax 35}
	
slave8OutputCurrentMaxThirtysix OBJECT-TYPE
    SYNTAX      DisplayString
    MAX-ACCESS  read-write
    STATUS      current
    DESCRIPTION
	"The second output Max. current alarm value of slave8"
    ::= { slave8OutputCurrentMax 36}
	
slave8OutputCurrentMaxThirtyseven OBJECT-TYPE
    SYNTAX      DisplayString
    MAX-ACCESS  read-write
    STATUS      current
    DESCRIPTION
	"The second output Max. current alarm value of slave8"
    ::= { slave8OutputCurrentMax 37}
	
slave8OutputCurrentMaxThirtyeight OBJECT-TYPE
    SYNTAX      DisplayString
    MAX-ACCESS  read-write
    STATUS      current
    DESCRIPTION
	"The second output Max. current alarm value of slave8"
    ::= { slave8OutputCurrentMax 38}
	
slave8OutputCurrentMaxThirtynine OBJECT-TYPE
    SYNTAX      DisplayString
    MAX-ACCESS  read-write
    STATUS      current
    DESCRIPTION
	"The second output Max. current alarm value of slave8"
    ::= { slave8OutputCurrentMax 39}
	
slave8OutputCurrentMaxFourty OBJECT-TYPE
    SYNTAX      DisplayString
    MAX-ACCESS  read-write
    STATUS      current
    DESCRIPTION
	"The second output Max. current alarm value of slave8"
    ::= { slave8OutputCurrentMax 40}
	
slave8OutputCurrentMaxFourtyone OBJECT-TYPE
    SYNTAX      DisplayString
    MAX-ACCESS  read-write
    STATUS      current
    DESCRIPTION
	"The second output Max. current alarm value of slave8"
    ::= { slave8OutputCurrentMax 41}
	
slave8OutputCurrentMaxFourtytwo OBJECT-TYPE
    SYNTAX      DisplayString
    MAX-ACCESS  read-write
    STATUS      current
    DESCRIPTION
	"The second output Max. current alarm value of slave8"
    ::= { slave8OutputCurrentMax 42}
	
	
-------------------------------slave8 output powerfactor------------------------	
slave8OutputPowerfactor OBJECT IDENTIFIER ::= { slave8 9}	

slave8OutputPowerfactorOne OBJECT-TYPE
    SYNTAX      DisplayString
    MAX-ACCESS  read-only
    STATUS      current
    DESCRIPTION
	"The ouput power factor of slave8." 
	::= { slave8OutputPowerfactor 1}

slave8OutputPowerfactorTwo OBJECT-TYPE
    SYNTAX      DisplayString
    MAX-ACCESS  read-only
    STATUS      current
    DESCRIPTION
	"The ouput power factor of slave8." 
	::= { slave8OutputPowerfactor 2}
	
slave8OutputPowerfactorThree OBJECT-TYPE
    SYNTAX      DisplayString
    MAX-ACCESS  read-only
    STATUS      current
    DESCRIPTION
	"The ouput power factor of slave8." 
	::= { slave8OutputPowerfactor 3}
	
slave8OutputPowerfactorFour OBJECT-TYPE
    SYNTAX      DisplayString
    MAX-ACCESS  read-only
    STATUS      current
    DESCRIPTION
	"The ouput power factor of slave8." 
	::= { slave8OutputPowerfactor 4}
		
slave8OutputPowerfactorFive OBJECT-TYPE
    SYNTAX      DisplayString
    MAX-ACCESS  read-only
    STATUS      current
    DESCRIPTION
	"The ouput power factor of slave8." 
	::= { slave8OutputPowerfactor 5}
	
slave8OutputPowerfactorSix OBJECT-TYPE
    SYNTAX      DisplayString
    MAX-ACCESS  read-only
    STATUS      current
    DESCRIPTION
	"The ouput power factor of slave8." 
	::= { slave8OutputPowerfactor 6}
	
slave8OutputPowerfactorSeven OBJECT-TYPE
    SYNTAX      DisplayString
    MAX-ACCESS  read-only
    STATUS      current
    DESCRIPTION
	"The ouput power factor of slave8." 
	::= { slave8OutputPowerfactor 7}	
	
slave8OutputPowerfactorEight OBJECT-TYPE
    SYNTAX      DisplayString
    MAX-ACCESS  read-only
    STATUS      current
    DESCRIPTION
	"The ouput power factor of slave8." 
	::= { slave8OutputPowerfactor 8}
	
slave8OutputPowerfactorNine OBJECT-TYPE
    SYNTAX      DisplayString
    MAX-ACCESS  read-only
    STATUS      current
    DESCRIPTION
	"The ouput power factor of slave8." 
	::= { slave8OutputPowerfactor 9}
		
slave8OutputPowerfactorTen OBJECT-TYPE
    SYNTAX      DisplayString
    MAX-ACCESS  read-only
    STATUS      current
    DESCRIPTION
	"The ouput power factor of slave8." 
	::= { slave8OutputPowerfactor 10}
		
slave8OutputPowerfactorEleven OBJECT-TYPE
    SYNTAX      DisplayString
    MAX-ACCESS  read-only
    STATUS      current
    DESCRIPTION
	"The ouput power factor of slave8." 
	::= { slave8OutputPowerfactor 11}
		
slave8OutputPowerfactorTwel OBJECT-TYPE
    SYNTAX      DisplayString
    MAX-ACCESS  read-only
    STATUS      current
    DESCRIPTION
	"The ouput power factor of slave8." 
	::= { slave8OutputPowerfactor 12}
		
slave8OutputPowerfactorThirteen OBJECT-TYPE
    SYNTAX      DisplayString
    MAX-ACCESS  read-only
    STATUS      current
    DESCRIPTION
	"The ouput power factor of slave8." 
	::= { slave8OutputPowerfactor 13}
		
slave8OutputPowerfactorFourteen OBJECT-TYPE
    SYNTAX      DisplayString
    MAX-ACCESS  read-only
    STATUS      current
    DESCRIPTION
	"The ouput power factor of slave8." 
	::= { slave8OutputPowerfactor 14}
		
slave8OutputPowerfactorFifteen OBJECT-TYPE
    SYNTAX      DisplayString
    MAX-ACCESS  read-only
    STATUS      current
    DESCRIPTION
	"The ouput power factor of slave8." 
	::= { slave8OutputPowerfactor 15}
		
slave8OutputPowerfactorSixteen OBJECT-TYPE
    SYNTAX      DisplayString
    MAX-ACCESS  read-only
    STATUS      current
    DESCRIPTION
	"The ouput power factor of slave8." 
	::= { slave8OutputPowerfactor 16}
		
slave8OutputPowerfactorSeventeen OBJECT-TYPE
    SYNTAX      DisplayString
    MAX-ACCESS  read-only
    STATUS      current
    DESCRIPTION
	"The ouput power factor of slave8." 
	::= { slave8OutputPowerfactor 17}
		
slave8OutputPowerfactorEighteen OBJECT-TYPE
    SYNTAX      DisplayString
    MAX-ACCESS  read-only
    STATUS      current
    DESCRIPTION
	"The ouput power factor of slave8." 
	::= { slave8OutputPowerfactor 18}
		
slave8OutputPowerfactorNineteen OBJECT-TYPE
    SYNTAX      DisplayString
    MAX-ACCESS  read-only
    STATUS      current
    DESCRIPTION
	"The ouput power factor of slave8." 
	::= { slave8OutputPowerfactor 19}
		
slave8OutputPowerfactorTwenty OBJECT-TYPE
    SYNTAX      DisplayString
    MAX-ACCESS  read-only
    STATUS      current
    DESCRIPTION
	"The ouput power factor of slave8." 
	::= { slave8OutputPowerfactor 20}
		
slave8OutputPowerfactorTwentyone OBJECT-TYPE
    SYNTAX      DisplayString
    MAX-ACCESS  read-only
    STATUS      current
    DESCRIPTION
	"The ouput power factor of slave8." 
	::= { slave8OutputPowerfactor 21}
		
slave8OutputPowerfactorTwentytwo OBJECT-TYPE
    SYNTAX      DisplayString
    MAX-ACCESS  read-only
    STATUS      current
    DESCRIPTION
	"The ouput power factor of slave8." 
	::= { slave8OutputPowerfactor 22}
		
slave8OutputPowerfactorTwentythree OBJECT-TYPE
    SYNTAX      DisplayString
    MAX-ACCESS  read-only
    STATUS      current
    DESCRIPTION
	"The ouput power factor of slave8." 
	::= { slave8OutputPowerfactor 23}
		
slave8OutputPowerfactorTwentyfour OBJECT-TYPE
    SYNTAX      DisplayString
    MAX-ACCESS  read-only
    STATUS      current
    DESCRIPTION
	"The ouput power factor of slave8." 
	::= { slave8OutputPowerfactor 24}
		
slave8OutputPowerfactorTwentyfive OBJECT-TYPE
    SYNTAX      DisplayString
    MAX-ACCESS  read-only
    STATUS      current
    DESCRIPTION
	"The ouput power factor of slave8." 
	::= { slave8OutputPowerfactor 25}
		
slave8OutputPowerfactorTwentysix OBJECT-TYPE
    SYNTAX      DisplayString
    MAX-ACCESS  read-only
    STATUS      current
    DESCRIPTION
	"The ouput power factor of slave8." 
	::= { slave8OutputPowerfactor 26}
		
slave8OutputPowerfactorTwentyseven OBJECT-TYPE
    SYNTAX      DisplayString
    MAX-ACCESS  read-only
    STATUS      current
    DESCRIPTION
	"The ouput power factor of slave8." 
	::= { slave8OutputPowerfactor 27}
		
slave8OutputPowerfactorTwentyeight OBJECT-TYPE
    SYNTAX      DisplayString
    MAX-ACCESS  read-only
    STATUS      current
    DESCRIPTION
	"The ouput power factor of slave8." 
	::= { slave8OutputPowerfactor 28}
		
slave8OutputPowerfactorTwentynine OBJECT-TYPE
    SYNTAX      DisplayString
    MAX-ACCESS  read-only
    STATUS      current
    DESCRIPTION
	"The ouput power factor of slave8." 
	::= { slave8OutputPowerfactor 29}
		
slave8OutputPowerfactorThirty OBJECT-TYPE
    SYNTAX      DisplayString
    MAX-ACCESS  read-only
    STATUS      current
    DESCRIPTION
	"The ouput power factor of slave8." 
	::= { slave8OutputPowerfactor 30}
		
slave8OutputPowerfactorThirtyone OBJECT-TYPE
    SYNTAX      DisplayString
    MAX-ACCESS  read-only
    STATUS      current
    DESCRIPTION
	"The ouput power factor of slave8." 
	::= { slave8OutputPowerfactor 31}
		
slave8OutputPowerfactorThirtytwo OBJECT-TYPE
    SYNTAX      DisplayString
    MAX-ACCESS  read-only
    STATUS      current
    DESCRIPTION
	"The ouput power factor of slave8." 
	::= { slave8OutputPowerfactor 32}
		
slave8OutputPowerfactorThirtythree OBJECT-TYPE
    SYNTAX      DisplayString
    MAX-ACCESS  read-only
    STATUS      current
    DESCRIPTION
	"The ouput power factor of slave8." 
	::= { slave8OutputPowerfactor 33}	
	
slave8OutputPowerfactorThirtyfour OBJECT-TYPE
    SYNTAX      DisplayString
    MAX-ACCESS  read-only
    STATUS      current
    DESCRIPTION
	"The ouput power factor of slave8." 
	::= { slave8OutputPowerfactor 34}
	
	
slave8OutputPowerfactorThirtyfive OBJECT-TYPE
    SYNTAX      DisplayString
    MAX-ACCESS  read-only
    STATUS      current
    DESCRIPTION
	"The ouput power factor of slave8." 
	::= { slave8OutputPowerfactor 35}
		
slave8OutputPowerfactorThirtysix OBJECT-TYPE
    SYNTAX      DisplayString
    MAX-ACCESS  read-only
    STATUS      current
    DESCRIPTION
	"The ouput power factor of slave8." 
	::= { slave8OutputPowerfactor 36}
		
slave8OutputPowerfactorThirtyseven OBJECT-TYPE
    SYNTAX      DisplayString
    MAX-ACCESS  read-only
    STATUS      current
    DESCRIPTION
	"The ouput power factor of slave8." 
	::= { slave8OutputPowerfactor 37}
		
slave8OutputPowerfactorThirtyeight OBJECT-TYPE
    SYNTAX      DisplayString
    MAX-ACCESS  read-only
    STATUS      current
    DESCRIPTION
	"The ouput power factor of slave8." 
	::= { slave8OutputPowerfactor 38}
		
slave8OutputPowerfactorThirtynine OBJECT-TYPE
    SYNTAX      DisplayString
    MAX-ACCESS  read-only
    STATUS      current
    DESCRIPTION
	"The ouput power factor of slave8." 
	::= { slave8OutputPowerfactor 39}
		
slave8OutputPowerfactorFourty OBJECT-TYPE
    SYNTAX      DisplayString
    MAX-ACCESS  read-only
    STATUS      current
    DESCRIPTION
	"The ouput power factor of slave8." 
	::= { slave8OutputPowerfactor 40}
		
slave8OutputPowerfactorFourtyone OBJECT-TYPE
    SYNTAX      DisplayString
    MAX-ACCESS  read-only
    STATUS      current
    DESCRIPTION
	"The ouput power factor of slave8." 
	::= { slave8OutputPowerfactor 41}
		
slave8OutputPowerfactorFourtytwo OBJECT-TYPE
    SYNTAX      DisplayString
    MAX-ACCESS  read-only
    STATUS      current
    DESCRIPTION
	"The ouput power factor of slave8." 
	::= { slave8OutputPowerfactor 42}	
	
-------------------------------slave8 output energy------------------------	
slave8OutputEnergy OBJECT IDENTIFIER ::= { slave8 10}

slave8OutputEnergyOne OBJECT-TYPE
    SYNTAX      DisplayString
    MAX-ACCESS  read-only
    STATUS      current
    DESCRIPTION
	"The ouput power of slave8." 
	::= { slave8OutputEnergy 1}

slave8OutputEnergyTwo OBJECT-TYPE
    SYNTAX      DisplayString
    MAX-ACCESS  read-only
    STATUS      current
    DESCRIPTION
	"The ouput power of slave8." 
	::= { slave8OutputEnergy 2}
	
slave8OutputEnergyThree OBJECT-TYPE
    SYNTAX      DisplayString
    MAX-ACCESS  read-only
    STATUS      current
    DESCRIPTION
	"The ouput power of slave8." 
	::= { slave8OutputEnergy 3}
	
slave8OutputEnergyFour OBJECT-TYPE
    SYNTAX      DisplayString
    MAX-ACCESS  read-only
    STATUS      current
    DESCRIPTION
	"The ouput power of slave8." 
	::= { slave8OutputEnergy 4}
		
slave8OutputEnergyFive OBJECT-TYPE
    SYNTAX      DisplayString
    MAX-ACCESS  read-only
    STATUS      current
    DESCRIPTION
	"The ouput power of slave8." 
	::= { slave8OutputEnergy 5}
	
slave8OutputEnergySix OBJECT-TYPE
    SYNTAX      DisplayString
    MAX-ACCESS  read-only
    STATUS      current
    DESCRIPTION
	"The ouput power of slave8." 
	::= { slave8OutputEnergy 6}
	
slave8OutputEnergySeven OBJECT-TYPE
    SYNTAX      DisplayString
    MAX-ACCESS  read-only
    STATUS      current
    DESCRIPTION
	"The ouput power of slave8." 
	::= { slave8OutputEnergy 7}	
	
slave8OutputEnergyEight OBJECT-TYPE
    SYNTAX      DisplayString
    MAX-ACCESS  read-only
    STATUS      current
    DESCRIPTION
	"The ouput power of slave8." 
	::= { slave8OutputEnergy 8}
	
slave8OutputEnergyNine OBJECT-TYPE
    SYNTAX      DisplayString
    MAX-ACCESS  read-only
    STATUS      current
    DESCRIPTION
	"The ouput power of slave8." 
	::= { slave8OutputEnergy 9}
		
slave8OutputEnergyTen OBJECT-TYPE
    SYNTAX      DisplayString
    MAX-ACCESS  read-only
    STATUS      current
    DESCRIPTION
	"The ouput power of slave8." 
	::= { slave8OutputEnergy 10}
		
slave8OutputEnergyEleven OBJECT-TYPE
    SYNTAX      DisplayString
    MAX-ACCESS  read-only
    STATUS      current
    DESCRIPTION
	"The ouput power of slave8." 
	::= { slave8OutputEnergy 11}
		
slave8OutputEnergyTwel OBJECT-TYPE
    SYNTAX      DisplayString
    MAX-ACCESS  read-only
    STATUS      current
    DESCRIPTION
	"The ouput power of slave8." 
	::= { slave8OutputEnergy 12}
		
slave8OutputEnergyThirteen OBJECT-TYPE
    SYNTAX      DisplayString
    MAX-ACCESS  read-only
    STATUS      current
    DESCRIPTION
	"The ouput power of slave8." 
	::= { slave8OutputEnergy 13}
		
slave8OutputEnergyFourteen OBJECT-TYPE
    SYNTAX      DisplayString
    MAX-ACCESS  read-only
    STATUS      current
    DESCRIPTION
	"The ouput power of slave8." 
	::= { slave8OutputEnergy 14}
		
slave8OutputEnergyFifteen OBJECT-TYPE
    SYNTAX      DisplayString
    MAX-ACCESS  read-only
    STATUS      current
    DESCRIPTION
	"The ouput power of slave8." 
	::= { slave8OutputEnergy 15}
		
slave8OutputEnergySixteen OBJECT-TYPE
    SYNTAX      DisplayString
    MAX-ACCESS  read-only
    STATUS      current
    DESCRIPTION
	"The ouput power of slave8." 
	::= { slave8OutputEnergy 16}
		
slave8OutputEnergySeventeen OBJECT-TYPE
    SYNTAX      DisplayString
    MAX-ACCESS  read-only
    STATUS      current
    DESCRIPTION
	"The ouput power of slave8." 
	::= { slave8OutputEnergy 17}
		
slave8OutputEnergyEighteen OBJECT-TYPE
    SYNTAX      DisplayString
    MAX-ACCESS  read-only
    STATUS      current
    DESCRIPTION
	"The ouput power of slave8." 
	::= { slave8OutputEnergy 18}
		
slave8OutputEnergyNineteen OBJECT-TYPE
    SYNTAX      DisplayString
    MAX-ACCESS  read-only
    STATUS      current
    DESCRIPTION
	"The ouput power of slave8." 
	::= { slave8OutputEnergy 19}
		
slave8OutputEnergyTwenty OBJECT-TYPE
    SYNTAX      DisplayString
    MAX-ACCESS  read-only
    STATUS      current
    DESCRIPTION
	"The ouput power of slave8." 
	::= { slave8OutputEnergy 20}
		
slave8OutputEnergyTwentyone OBJECT-TYPE
    SYNTAX      DisplayString
    MAX-ACCESS  read-only
    STATUS      current
    DESCRIPTION
	"The ouput power of slave8." 
	::= { slave8OutputEnergy 21}
		
slave8OutputEnergyTwentytwo OBJECT-TYPE
    SYNTAX      DisplayString
    MAX-ACCESS  read-only
    STATUS      current
    DESCRIPTION
	"The ouput power of slave8." 
	::= { slave8OutputEnergy 22}
		
slave8OutputEnergyTwentythree OBJECT-TYPE
    SYNTAX      DisplayString
    MAX-ACCESS  read-only
    STATUS      current
    DESCRIPTION
	"The ouput power of slave8." 
	::= { slave8OutputEnergy 23}
		
slave8OutputEnergyTwentyfour OBJECT-TYPE
    SYNTAX      DisplayString
    MAX-ACCESS  read-only
    STATUS      current
    DESCRIPTION
	"The ouput power of slave8." 
	::= { slave8OutputEnergy 24}
		
slave8OutputEnergyTwentyfive OBJECT-TYPE
    SYNTAX      DisplayString
    MAX-ACCESS  read-only
    STATUS      current
    DESCRIPTION
	"The ouput power of slave8." 
	::= { slave8OutputEnergy 25}
		
slave8OutputEnergyTwentysix OBJECT-TYPE
    SYNTAX      DisplayString
    MAX-ACCESS  read-only
    STATUS      current
    DESCRIPTION
	"The ouput power of slave8." 
	::= { slave8OutputEnergy 26}
		
slave8OutputEnergyTwentyseven OBJECT-TYPE
    SYNTAX      DisplayString
    MAX-ACCESS  read-only
    STATUS      current
    DESCRIPTION
	"The ouput power of slave8." 
	::= { slave8OutputEnergy 27}
		
slave8OutputEnergyTwentyeight OBJECT-TYPE
    SYNTAX      DisplayString
    MAX-ACCESS  read-only
    STATUS      current
    DESCRIPTION
	"The ouput power of slave8." 
	::= { slave8OutputEnergy 28}
		
slave8OutputEnergyTwentynine OBJECT-TYPE
    SYNTAX      DisplayString
    MAX-ACCESS  read-only
    STATUS      current
    DESCRIPTION
	"The ouput power of slave8." 
	::= { slave8OutputEnergy 29}
		
slave8OutputEnergyThirty OBJECT-TYPE
    SYNTAX      DisplayString
    MAX-ACCESS  read-only
    STATUS      current
    DESCRIPTION
	"The ouput power of slave8." 
	::= { slave8OutputEnergy 30}
		
slave8OutputEnergyThirtyone OBJECT-TYPE
    SYNTAX      DisplayString
    MAX-ACCESS  read-only
    STATUS      current
    DESCRIPTION
	"The ouput power of slave8." 
	::= { slave8OutputEnergy 31}
		
slave8OutputEnergyThirtytwo OBJECT-TYPE
    SYNTAX      DisplayString
    MAX-ACCESS  read-only
    STATUS      current
    DESCRIPTION
	"The ouput power of slave8." 
	::= { slave8OutputEnergy 32}
		
slave8OutputEnergyThirtythree OBJECT-TYPE
    SYNTAX      DisplayString
    MAX-ACCESS  read-only
    STATUS      current
    DESCRIPTION
	"The ouput power of slave8." 
	::= { slave8OutputEnergy 33}	
	
slave8OutputEnergyThirtyfour OBJECT-TYPE
    SYNTAX      DisplayString
    MAX-ACCESS  read-only
    STATUS      current
    DESCRIPTION
	"The ouput power of slave8." 
	::= { slave8OutputEnergy 34}
	
	
slave8OutputEnergyThirtyfive OBJECT-TYPE
    SYNTAX      DisplayString
    MAX-ACCESS  read-only
    STATUS      current
    DESCRIPTION
	"The ouput power of slave8." 
	::= { slave8OutputEnergy 35}
		
slave8OutputEnergyThirtysix OBJECT-TYPE
    SYNTAX      DisplayString
    MAX-ACCESS  read-only
    STATUS      current
    DESCRIPTION
	"The ouput power of slave8." 
	::= { slave8OutputEnergy 36}
		
slave8OutputEnergyThirtyseven OBJECT-TYPE
    SYNTAX      DisplayString
    MAX-ACCESS  read-only
    STATUS      current
    DESCRIPTION
	"The ouput power of slave8." 
	::= { slave8OutputEnergy 37}
		
slave8OutputEnergyThirtyeight OBJECT-TYPE
    SYNTAX      DisplayString
    MAX-ACCESS  read-only
    STATUS      current
    DESCRIPTION
	"The ouput power of slave8." 
	::= { slave8OutputEnergy 38}
		
slave8OutputEnergyThirtynine OBJECT-TYPE
    SYNTAX      DisplayString
    MAX-ACCESS  read-only
    STATUS      current
    DESCRIPTION
	"The ouput power of slave8." 
	::= { slave8OutputEnergy 39}
		
slave8OutputEnergyFourty OBJECT-TYPE
    SYNTAX      DisplayString
    MAX-ACCESS  read-only
    STATUS      current
    DESCRIPTION
	"The ouput power of slave8." 
	::= { slave8OutputEnergy 40}
		
slave8OutputEnergyFourtyone OBJECT-TYPE
    SYNTAX      DisplayString
    MAX-ACCESS  read-only
    STATUS      current
    DESCRIPTION
	"The ouput power of slave8." 
	::= { slave8OutputEnergy 41}
		
slave8OutputEnergyFourtytwo OBJECT-TYPE
    SYNTAX      DisplayString
    MAX-ACCESS  read-only
    STATUS      current
    DESCRIPTION
	"The ouput power of slave8." 
	::= { slave8OutputEnergy 42}	


	
	
	
	
-------------------------------slave9 information--------------------
slave9 OBJECT IDENTIFIER ::= { pdu 10}
slave9Information OBJECT IDENTIFIER ::= { slave9 1}
slave9Name OBJECT-TYPE
    SYNTAX      DisplayString
    MAX-ACCESS  read-write
    STATUS      current
    DESCRIPTION
	"This is the first device."
    ::= { slave9Information 1}
    
slave9Type OBJECT-TYPE
    SYNTAX      DisplayString
    MAX-ACCESS  read-only
    STATUS      current
    DESCRIPTION
	"This is device type "
    ::= { slave9Information 2}
    
slave9OutputNumber OBJECT-TYPE 
    SYNTAX      Integer32
    MAX-ACCESS  read-only
    STATUS      current
    DESCRIPTION
	"This is the number of output bits"
	::= { slave9Information 3}
	
slave9MacAdress OBJECT-TYPE
    SYNTAX      DisplayString
    MAX-ACCESS  read-only
    STATUS      current
    DESCRIPTION
	"This is device MAC adress"
    ::= { slave9Information 4}	

slave9Vison OBJECT-TYPE
    SYNTAX      DisplayString
    MAX-ACCESS  read-only
    STATUS      current
    DESCRIPTION
	"This is device vison "
    ::= { slave9Information 5}

slave9Frequency OBJECT-TYPE
    SYNTAX      Integer32
    MAX-ACCESS  read-only
    STATUS      current
    DESCRIPTION
	"This is device frequency "
    ::= { slave9Information 6}
	
slave9Emission OBJECT-TYPE
    SYNTAX      DisplayString
    MAX-ACCESS  read-only
    STATUS      current
    DESCRIPTION
	"This is device emission "
    ::= { slave9Information 7}	
	
slave9RunTime OBJECT-TYPE
    SYNTAX      DisplayString
    MAX-ACCESS  read-only
    STATUS      current
    DESCRIPTION
	"This is device running time "
    ::= { slave9Information 8}	

slave9BuzzerSwitch OBJECT-TYPE
    SYNTAX      DisplayString
    MAX-ACCESS  read-write
    STATUS      current
    DESCRIPTION
	"This is device buzzer switch."
    ::= { slave9Information 9}	

	
-------------------------------slave9 phase--------------------
slave9Phase OBJECT IDENTIFIER ::= { slave9 2}	
	
slave9PhaseOne OBJECT IDENTIFIER ::= { slave9Phase 1}	    
slave9PhaseOneCurrent OBJECT-TYPE
    SYNTAX      DisplayString
    MAX-ACCESS  read-only
    STATUS      current
    DESCRIPTION
	"The power of phase one"
    ::= { slave9PhaseOne 1}

slave9PhaseOneVoltage OBJECT-TYPE
    SYNTAX      DisplayString
    MAX-ACCESS  read-only
    STATUS      current
    DESCRIPTION
	"The power of phase one"
    ::= { slave9PhaseOne 2}

slave9PhaseOnePower OBJECT-TYPE
    SYNTAX      DisplayString
    MAX-ACCESS  read-only
    STATUS      current
    DESCRIPTION
	"The power of phase one"
    ::= { slave9PhaseOne 3}
	
slave9PhaseOnePowerfactor OBJECT-TYPE
    SYNTAX      DisplayString
    MAX-ACCESS  read-only
    STATUS      current
    DESCRIPTION
	"The power of phase one"
    ::= { slave9PhaseOne 4}	
	
slave9PhaseOneEnergy OBJECT-TYPE
    SYNTAX      DisplayString
    MAX-ACCESS  read-only
    STATUS      current
    DESCRIPTION
	"The power of phase one"
    ::= { slave9PhaseOne 5}	
		
slave9PhaseOneCurrentMin OBJECT-TYPE
    SYNTAX      DisplayString
    MAX-ACCESS  read-write
    STATUS      current
    DESCRIPTION
	"The power of phase one"
    ::= { slave9PhaseOne 6}	
	
slave9PhaseOneCurrentMinCritical OBJECT-TYPE
    SYNTAX      DisplayString
    MAX-ACCESS  read-write
    STATUS      current
    DESCRIPTION
	"The power of phase one"
    ::= { slave9PhaseOne 7}
	
slave9PhaseOneCurrentMaxCritical OBJECT-TYPE
    SYNTAX      DisplayString
    MAX-ACCESS  read-write
    STATUS      current
    DESCRIPTION
	"The power of phase one"
    ::= { slave9PhaseOne 8}
	
slave9PhaseOneCurrentMax OBJECT-TYPE
    SYNTAX      DisplayString
    MAX-ACCESS  read-write
    STATUS      current
    DESCRIPTION
	"The power of phase one"
    ::= { slave9PhaseOne 9}
	
slave9PhaseOneVoltageMin OBJECT-TYPE
    SYNTAX      DisplayString
    MAX-ACCESS  read-write
    STATUS      current
    DESCRIPTION
	"The power of phase one"
    ::= { slave9PhaseOne 10}
	
slave9PhaseOneVoltageMinCritical OBJECT-TYPE
    SYNTAX      DisplayString
    MAX-ACCESS  read-write
    STATUS      current
    DESCRIPTION
	"The power of phase one"
    ::= { slave9PhaseOne 11}

slave9PhaseOneVoltageMaxCritical OBJECT-TYPE
    SYNTAX      DisplayString
    MAX-ACCESS  read-write
    STATUS      current
    DESCRIPTION
	"The power of phase one"
    ::= { slave9PhaseOne 12}
	
slave9PhaseOneVoltageMax OBJECT-TYPE
    SYNTAX      DisplayString
    MAX-ACCESS  read-write
    STATUS      current
    DESCRIPTION
	"The power of phase one"
    ::= { slave9PhaseOne 13}


slave9PhaseTwo OBJECT IDENTIFIER ::= { slave9Phase 2}	    
slave9PhaseTwoCurrent OBJECT-TYPE
    SYNTAX      DisplayString
    MAX-ACCESS  read-only
    STATUS      current
    DESCRIPTION
	"The power of phase one"
    ::= { slave9PhaseTwo 1}

slave9PhaseTwoVoltage OBJECT-TYPE
    SYNTAX      DisplayString
    MAX-ACCESS  read-only
    STATUS      current
    DESCRIPTION
	"The power of phase one"
    ::= { slave9PhaseTwo 2}

slave9PhaseTwoPower OBJECT-TYPE
    SYNTAX      DisplayString
    MAX-ACCESS  read-only
    STATUS      current
    DESCRIPTION
	"The power of phase one"
    ::= { slave9PhaseTwo 3}
	
slave9PhaseTwoPowerfactor OBJECT-TYPE
    SYNTAX      DisplayString
    MAX-ACCESS  read-only
    STATUS      current
    DESCRIPTION
	"The power of phase one"
    ::= { slave9PhaseTwo 4}	
	
slave9PhaseTwoEnergy OBJECT-TYPE
    SYNTAX      DisplayString
    MAX-ACCESS  read-only
    STATUS      current
    DESCRIPTION
	"The power of phase one"
    ::= { slave9PhaseTwo 5}	
		
slave9PhaseTwoCurrentMin OBJECT-TYPE
    SYNTAX      DisplayString
    MAX-ACCESS  read-write
    STATUS      current
    DESCRIPTION
	"The power of phase one"
    ::= { slave9PhaseTwo 6}	
	
slave9PhaseTwoCurrentMinCritical OBJECT-TYPE
    SYNTAX      DisplayString
    MAX-ACCESS  read-write
    STATUS      current
    DESCRIPTION
	"The power of phase one"
    ::= { slave9PhaseTwo 7}
	
slave9PhaseTwoCurrentMaxCritical OBJECT-TYPE
    SYNTAX      DisplayString
    MAX-ACCESS  read-write
    STATUS      current
    DESCRIPTION
	"The power of phase one"
    ::= { slave9PhaseTwo 8}
	
slave9PhaseTwoCurrentMax OBJECT-TYPE
    SYNTAX      DisplayString
    MAX-ACCESS  read-write
    STATUS      current
    DESCRIPTION
	"The power of phase one"
    ::= { slave9PhaseTwo 9}
	
slave9PhaseTwoVoltageMin OBJECT-TYPE
    SYNTAX      DisplayString
    MAX-ACCESS  read-write
    STATUS      current
    DESCRIPTION
	"The power of phase one"
    ::= { slave9PhaseTwo 10}
	
slave9PhaseTwoVoltageMinCritical OBJECT-TYPE
    SYNTAX      DisplayString
    MAX-ACCESS  read-write
    STATUS      current
    DESCRIPTION
	"The power of phase one"
    ::= { slave9PhaseTwo 11}

slave9PhaseTwoVoltageMaxCritical OBJECT-TYPE
    SYNTAX      DisplayString
    MAX-ACCESS  read-write
    STATUS      current
    DESCRIPTION
	"The power of phase one"
    ::= { slave9PhaseTwo 12}
	
slave9PhaseTwoVoltageMax OBJECT-TYPE
    SYNTAX      DisplayString
    MAX-ACCESS  read-write
    STATUS      current
    DESCRIPTION
	"The power of phase one"
    ::= { slave9PhaseTwo 13}
	
	
slave9PhaseThree OBJECT IDENTIFIER ::= { slave9Phase 3}	    
slave9PhaseThreeCurrent OBJECT-TYPE
    SYNTAX      DisplayString
    MAX-ACCESS  read-only
    STATUS      current
    DESCRIPTION
	"The power of phase one"
    ::= { slave9PhaseThree 1}

slave9PhaseThreeVoltage OBJECT-TYPE
    SYNTAX      DisplayString
    MAX-ACCESS  read-only
    STATUS      current
    DESCRIPTION
	"The power of phase one"
    ::= { slave9PhaseThree 2}

slave9PhaseThreePower OBJECT-TYPE
    SYNTAX      DisplayString
    MAX-ACCESS  read-only
    STATUS      current
    DESCRIPTION
	"The power of phase one"
    ::= { slave9PhaseThree 3}
	
slave9PhaseThreePowerfactor OBJECT-TYPE
    SYNTAX      DisplayString
    MAX-ACCESS  read-only
    STATUS      current
    DESCRIPTION
	"The power of phase one"
    ::= { slave9PhaseThree 4}	
	
slave9PhaseThreeEnergy OBJECT-TYPE
    SYNTAX      DisplayString
    MAX-ACCESS  read-only
    STATUS      current
    DESCRIPTION
	"The power of phase one"
    ::= { slave9PhaseThree 5}	
		
slave9PhaseThreeCurrentMin OBJECT-TYPE
    SYNTAX      DisplayString
    MAX-ACCESS  read-write
    STATUS      current
    DESCRIPTION
	"The power of phase one"
    ::= { slave9PhaseThree 6}	
	
slave9PhaseThreeCurrentMinCritical OBJECT-TYPE
    SYNTAX      DisplayString
    MAX-ACCESS  read-write
    STATUS      current
    DESCRIPTION
	"The power of phase one"
    ::= { slave9PhaseThree 7}
	
slave9PhaseThreeCurrentMaxCritical OBJECT-TYPE
    SYNTAX      DisplayString
    MAX-ACCESS  read-write
    STATUS      current
    DESCRIPTION
	"The power of phase one"
    ::= { slave9PhaseThree 8}
	
slave9PhaseThreeCurrentMax OBJECT-TYPE
    SYNTAX      DisplayString
    MAX-ACCESS  read-write
    STATUS      current
    DESCRIPTION
	"The power of phase one"
    ::= { slave9PhaseThree 9}
	
slave9PhaseThreeVoltageMin OBJECT-TYPE
    SYNTAX      DisplayString
    MAX-ACCESS  read-write
    STATUS      current
    DESCRIPTION
	"The power of phase one"
    ::= { slave9PhaseThree 10}
	
slave9PhaseThreeVoltageMinCritical OBJECT-TYPE
    SYNTAX      DisplayString
    MAX-ACCESS  read-write
    STATUS      current
    DESCRIPTION
	"The power of phase one"
    ::= { slave9PhaseThree 11}

slave9PhaseThreeVoltageMaxCritical OBJECT-TYPE
    SYNTAX      DisplayString
    MAX-ACCESS  read-write
    STATUS      current
    DESCRIPTION
	"The power of phase one"
    ::= { slave9PhaseThree 12}
	
slave9PhaseThreeVoltageMax OBJECT-TYPE
    SYNTAX      DisplayString
    MAX-ACCESS  read-write
    STATUS      current
    DESCRIPTION
	"The power of phase one"
    ::= { slave9PhaseThree 13}
	
	
-------------------------------slave9 circuit--------------------	
slave9Circuit OBJECT IDENTIFIER ::= { slave9 3}	

slave9CircuitOne OBJECT IDENTIFIER ::= { slave9Circuit 1}	    
slave9CircuitOneBreaker OBJECT-TYPE
    SYNTAX      DisplayString
    MAX-ACCESS  read-only
    STATUS      current
    DESCRIPTION
	"The power of phase one"
    ::= { slave9CircuitOne 1}
	
slave9CircuitOneManagementBit OBJECT-TYPE
    SYNTAX      DisplayString
    MAX-ACCESS  read-only
    STATUS      current
    DESCRIPTION
	"The power of phase one"
    ::= { slave9CircuitOne 2}	

slave9CircuitOneCurrent OBJECT-TYPE
    SYNTAX      DisplayString
    MAX-ACCESS  read-only
    STATUS      current
    DESCRIPTION
	"The power of phase one"
    ::= { slave9CircuitOne 3}

slave9CircuitOneVoltage OBJECT-TYPE
    SYNTAX      DisplayString
    MAX-ACCESS  read-only
    STATUS      current
    DESCRIPTION
	"The power of phase one"
    ::= { slave9CircuitOne 4}

slave9CircuitOneEnergy OBJECT-TYPE
    SYNTAX      DisplayString
    MAX-ACCESS  read-only
    STATUS      current
    DESCRIPTION
	"The power of phase one"
    ::= { slave9CircuitOne 5}	
	
slave9CircuitOnePower OBJECT-TYPE
    SYNTAX      DisplayString
    MAX-ACCESS  read-only
    STATUS      current
    DESCRIPTION
	"The power of phase one"
    ::= { slave9CircuitOne 6}
	
slave9CircuitOneCurrentMin OBJECT-TYPE
    SYNTAX      DisplayString
    MAX-ACCESS  read-write
    STATUS      current
    DESCRIPTION
	"The power of phase one"
    ::= { slave9CircuitOne 7}	
	
slave9CircuitOneCurrentMinCritical OBJECT-TYPE
    SYNTAX      DisplayString
    MAX-ACCESS  read-write
    STATUS      current
    DESCRIPTION
	"The power of phase one"
    ::= { slave9CircuitOne 8}
	
slave9CircuitOneCurrentMaxCritical OBJECT-TYPE
    SYNTAX      DisplayString
    MAX-ACCESS  read-write
    STATUS      current
    DESCRIPTION
	"The power of phase one"
    ::= { slave9CircuitOne 9}
	
slave9CircuitOneCurrentMax OBJECT-TYPE
    SYNTAX      DisplayString
    MAX-ACCESS  read-write
    STATUS      current
    DESCRIPTION
	"The power of phase one"
    ::= { slave9CircuitOne 10}
	

slave9CircuitTwo OBJECT IDENTIFIER ::= { slave9Circuit 2}	    
slave9CircuitTwoBreaker OBJECT-TYPE
    SYNTAX      DisplayString
    MAX-ACCESS  read-only
    STATUS      current
    DESCRIPTION
	"The power of phase one"
    ::= { slave9CircuitTwo 1}
	
slave9CircuitTwoManagementBit OBJECT-TYPE
    SYNTAX      DisplayString
    MAX-ACCESS  read-only
    STATUS      current
    DESCRIPTION
	"The power of phase one"
    ::= { slave9CircuitTwo 2}	

slave9CircuitTwoCurrent OBJECT-TYPE
    SYNTAX      DisplayString
    MAX-ACCESS  read-only
    STATUS      current
    DESCRIPTION
	"The power of phase one"
    ::= { slave9CircuitTwo 3}

slave9CircuitTwoVoltage OBJECT-TYPE
    SYNTAX      DisplayString
    MAX-ACCESS  read-only
    STATUS      current
    DESCRIPTION
	"The power of phase one"
    ::= { slave9CircuitTwo 4}

slave9CircuitTwoEnergy OBJECT-TYPE
    SYNTAX      DisplayString
    MAX-ACCESS  read-only
    STATUS      current
    DESCRIPTION
	"The power of phase one"
    ::= { slave9CircuitTwo 5}	
	
slave9CircuitTwoPower OBJECT-TYPE
    SYNTAX      DisplayString
    MAX-ACCESS  read-only
    STATUS      current
    DESCRIPTION
	"The power of phase one"
    ::= { slave9CircuitTwo 6}
	
slave9CircuitTwoCurrentMin OBJECT-TYPE
    SYNTAX      DisplayString
    MAX-ACCESS  read-write
    STATUS      current
    DESCRIPTION
	"The power of phase one"
    ::= { slave9CircuitTwo 7}	
	
slave9CircuitTwoCurrentMinCritical OBJECT-TYPE
    SYNTAX      DisplayString
    MAX-ACCESS  read-write
    STATUS      current
    DESCRIPTION
	"The power of phase one"
    ::= { slave9CircuitTwo 8}
	
slave9CircuitTwoCurrentMaxCritical OBJECT-TYPE
    SYNTAX      DisplayString
    MAX-ACCESS  read-write
    STATUS      current
    DESCRIPTION
	"The power of phase one"
    ::= { slave9CircuitTwo 9}
	
slave9CircuitTwoCurrentMax OBJECT-TYPE
    SYNTAX      DisplayString
    MAX-ACCESS  read-write
    STATUS      current
    DESCRIPTION
	"The power of phase one"
    ::= { slave9CircuitTwo 10}
	
	
slave9CircuitThree OBJECT IDENTIFIER ::= { slave9Circuit 3}	    
slave9CircuitThreeBreaker OBJECT-TYPE
    SYNTAX      DisplayString
    MAX-ACCESS  read-only
    STATUS      current
    DESCRIPTION
	"The power of phase one"
    ::= { slave9CircuitThree 1}
	
slave9CircuitThreeManagementBit OBJECT-TYPE
    SYNTAX      DisplayString
    MAX-ACCESS  read-only
    STATUS      current
    DESCRIPTION
	"The power of phase one"
    ::= { slave9CircuitThree 2}	

slave9CircuitThreeCurrent OBJECT-TYPE
    SYNTAX      DisplayString
    MAX-ACCESS  read-only
    STATUS      current
    DESCRIPTION
	"The power of phase one"
    ::= { slave9CircuitThree 3}

slave9CircuitThreeVoltage OBJECT-TYPE
    SYNTAX      DisplayString
    MAX-ACCESS  read-only
    STATUS      current
    DESCRIPTION
	"The power of phase one"
    ::= { slave9CircuitThree 4}

slave9CircuitThreeEnergy OBJECT-TYPE
    SYNTAX      DisplayString
    MAX-ACCESS  read-only
    STATUS      current
    DESCRIPTION
	"The power of phase one"
    ::= { slave9CircuitThree 5}	
	
slave9CircuitThreePower OBJECT-TYPE
    SYNTAX      DisplayString
    MAX-ACCESS  read-only
    STATUS      current
    DESCRIPTION
	"The power of phase one"
    ::= { slave9CircuitThree 6}
	
slave9CircuitThreeCurrentMin OBJECT-TYPE
    SYNTAX      DisplayString
    MAX-ACCESS  read-write
    STATUS      current
    DESCRIPTION
	"The power of phase one"
    ::= { slave9CircuitThree 7}	
	
slave9CircuitThreeCurrentMinCritical OBJECT-TYPE
    SYNTAX      DisplayString
    MAX-ACCESS  read-write
    STATUS      current
    DESCRIPTION
	"The power of phase one"
    ::= { slave9CircuitThree 8}
	
slave9CircuitThreeCurrentMaxCritical OBJECT-TYPE
    SYNTAX      DisplayString
    MAX-ACCESS  read-write
    STATUS      current
    DESCRIPTION
	"The power of phase one"
    ::= { slave9CircuitThree 9}
	
slave9CircuitThreeCurrentMax OBJECT-TYPE
    SYNTAX      DisplayString
    MAX-ACCESS  read-write
    STATUS      current
    DESCRIPTION
	"The power of phase one"
    ::= { slave9CircuitThree 10}
	
	
slave9CircuitFour OBJECT IDENTIFIER ::= { slave9Circuit 4}	    
slave9CircuitFourBreaker OBJECT-TYPE
    SYNTAX      DisplayString
    MAX-ACCESS  read-only
    STATUS      current
    DESCRIPTION
	"The power of phase one"
    ::= { slave9CircuitFour 1}
	
slave9CircuitFourManagementBit OBJECT-TYPE
    SYNTAX      DisplayString
    MAX-ACCESS  read-only
    STATUS      current
    DESCRIPTION
	"The power of phase one"
    ::= { slave9CircuitFour 2}	

slave9CircuitFourCurrent OBJECT-TYPE
    SYNTAX      DisplayString
    MAX-ACCESS  read-only
    STATUS      current
    DESCRIPTION
	"The power of phase one"
    ::= { slave9CircuitFour 3}

slave9CircuitFourVoltage OBJECT-TYPE
    SYNTAX      DisplayString
    MAX-ACCESS  read-only
    STATUS      current
    DESCRIPTION
	"The power of phase one"
    ::= { slave9CircuitFour 4}

slave9CircuitFourEnergy OBJECT-TYPE
    SYNTAX      DisplayString
    MAX-ACCESS  read-only
    STATUS      current
    DESCRIPTION
	"The power of phase one"
    ::= { slave9CircuitFour 5}	
	
slave9CircuitFourPower OBJECT-TYPE
    SYNTAX      DisplayString
    MAX-ACCESS  read-only
    STATUS      current
    DESCRIPTION
	"The power of phase one"
    ::= { slave9CircuitFour 6}
	
slave9CircuitFourCurrentMin OBJECT-TYPE
    SYNTAX      DisplayString
    MAX-ACCESS  read-write
    STATUS      current
    DESCRIPTION
	"The power of phase one"
    ::= { slave9CircuitFour 7}	
	
slave9CircuitFourCurrentMinCritical OBJECT-TYPE
    SYNTAX      DisplayString
    MAX-ACCESS  read-write
    STATUS      current
    DESCRIPTION
	"The power of phase one"
    ::= { slave9CircuitFour 8}
	
slave9CircuitFourCurrentMaxCritical OBJECT-TYPE
    SYNTAX      DisplayString
    MAX-ACCESS  read-write
    STATUS      current
    DESCRIPTION
	"The power of phase one"
    ::= { slave9CircuitFour 9}
	
slave9CircuitFourCurrentMax OBJECT-TYPE
    SYNTAX      DisplayString
    MAX-ACCESS  read-write
    STATUS      current
    DESCRIPTION
	"The power of phase one"
    ::= { slave9CircuitFour 10}
	
	
slave9CircuitFive OBJECT IDENTIFIER ::= { slave9Circuit 5}	    
slave9CircuitFiveBreaker OBJECT-TYPE
    SYNTAX      DisplayString
    MAX-ACCESS  read-only
    STATUS      current
    DESCRIPTION
	"The power of phase one"
    ::= { slave9CircuitFive 1}
	
slave9CircuitFiveManagementBit OBJECT-TYPE
    SYNTAX      DisplayString
    MAX-ACCESS  read-only
    STATUS      current
    DESCRIPTION
	"The power of phase one"
    ::= { slave9CircuitFive 2}	

slave9CircuitFiveCurrent OBJECT-TYPE
    SYNTAX      DisplayString
    MAX-ACCESS  read-only
    STATUS      current
    DESCRIPTION
	"The power of phase one"
    ::= { slave9CircuitFive 3}

slave9CircuitFiveVoltage OBJECT-TYPE
    SYNTAX      DisplayString
    MAX-ACCESS  read-only
    STATUS      current
    DESCRIPTION
	"The power of phase one"
    ::= { slave9CircuitFive 4}

slave9CircuitFiveEnergy OBJECT-TYPE
    SYNTAX      DisplayString
    MAX-ACCESS  read-only
    STATUS      current
    DESCRIPTION
	"The power of phase one"
    ::= { slave9CircuitFive 5}	
	
slave9CircuitFivePower OBJECT-TYPE
    SYNTAX      DisplayString
    MAX-ACCESS  read-only
    STATUS      current
    DESCRIPTION
	"The power of phase one"
    ::= { slave9CircuitFive 6}
		
slave9CircuitFiveCurrentMin OBJECT-TYPE
    SYNTAX      DisplayString
    MAX-ACCESS  read-write
    STATUS      current
    DESCRIPTION
	"The power of phase one"
    ::= { slave9CircuitFive 7}	
	
slave9CircuitFiveCurrentMinCritical OBJECT-TYPE
    SYNTAX      DisplayString
    MAX-ACCESS  read-write
    STATUS      current
    DESCRIPTION
	"The power of phase one"
    ::= { slave9CircuitFive 8}
	
slave9CircuitFiveCurrentMaxCritical OBJECT-TYPE
    SYNTAX      DisplayString
    MAX-ACCESS  read-write
    STATUS      current
    DESCRIPTION
	"The power of phase one"
    ::= { slave9CircuitFive 9}
	
slave9CircuitFiveCurrentMax OBJECT-TYPE
    SYNTAX      DisplayString
    MAX-ACCESS  read-write
    STATUS      current
    DESCRIPTION
	"The power of phase one"
    ::= { slave9CircuitFive 10}

	
slave9CircuitSix OBJECT IDENTIFIER ::= { slave9Circuit 6}	    
slave9CircuitSixBreaker OBJECT-TYPE
    SYNTAX      DisplayString
    MAX-ACCESS  read-only
    STATUS      current
    DESCRIPTION
	"The power of phase one"
    ::= { slave9CircuitSix 1}
	
slave9CircuitSixManagementBit OBJECT-TYPE
    SYNTAX      DisplayString
    MAX-ACCESS  read-only
    STATUS      current
    DESCRIPTION
	"The power of phase one"
    ::= { slave9CircuitSix 2}	

slave9CircuitSixCurrent OBJECT-TYPE
    SYNTAX      DisplayString
    MAX-ACCESS  read-only
    STATUS      current
    DESCRIPTION
	"The power of phase one"
    ::= { slave9CircuitSix 3}

slave9CircuitSixVoltage OBJECT-TYPE
    SYNTAX      DisplayString
    MAX-ACCESS  read-only
    STATUS      current
    DESCRIPTION
	"The power of phase one"
    ::= { slave9CircuitSix 4}

slave9CircuitSixEnergy OBJECT-TYPE
    SYNTAX      DisplayString
    MAX-ACCESS  read-only
    STATUS      current
    DESCRIPTION
	"The power of phase one"
    ::= { slave9CircuitSix 5}	
	
slave9CircuitSixPower OBJECT-TYPE
    SYNTAX      DisplayString
    MAX-ACCESS  read-only
    STATUS      current
    DESCRIPTION
	"The power of phase one"
    ::= { slave9CircuitSix 6}
	
slave9CircuitSixCurrentMin OBJECT-TYPE
    SYNTAX      DisplayString
    MAX-ACCESS  read-write
    STATUS      current
    DESCRIPTION
	"The power of phase one"
    ::= { slave9CircuitSix 7}	
	
slave9CircuitSixCurrentMinCritical OBJECT-TYPE
    SYNTAX      DisplayString
    MAX-ACCESS  read-write
    STATUS      current
    DESCRIPTION
	"The power of phase one"
    ::= { slave9CircuitSix 8}
	
slave9CircuitSixCurrentMaxCritical OBJECT-TYPE
    SYNTAX      DisplayString
    MAX-ACCESS  read-write
    STATUS      current
    DESCRIPTION
	"The power of phase one"
    ::= { slave9CircuitSix 9}
	
slave9CircuitSixCurrentMax OBJECT-TYPE
    SYNTAX      DisplayString
    MAX-ACCESS  read-write
    STATUS      current
    DESCRIPTION
	"The power of phase one"
    ::= { slave9CircuitSix 10}

	
-------------------------------slave9 sensor------------------------	
slave9Sensor OBJECT IDENTIFIER ::= { slave9 4}
slave9SensorTemperatureOne OBJECT-TYPE
    SYNTAX      DisplayString
    MAX-ACCESS  read-only
    STATUS      current
    DESCRIPTION
	"This is the first device."
    ::= { slave9Sensor 1}
	
slave9SensorTemperatureTwo OBJECT-TYPE
    SYNTAX      DisplayString
    MAX-ACCESS  read-only
    STATUS      current
    DESCRIPTION
	"This is the first device."
    ::= { slave9Sensor 2}

slave9SensorHumidityOne OBJECT-TYPE
    SYNTAX      DisplayString
    MAX-ACCESS  read-only
    STATUS      current
    DESCRIPTION
	"This is the first device."
    ::= { slave9Sensor 3}

slave9SensorHumidityTwo OBJECT-TYPE
    SYNTAX      DisplayString
    MAX-ACCESS  read-only
    STATUS      current
    DESCRIPTION
	"This is the first device."
    ::= { slave9Sensor 4}	

slave9SensorDoorOne OBJECT-TYPE
    SYNTAX      DisplayString
    MAX-ACCESS  read-only
    STATUS      current
    DESCRIPTION
	"This is the first device."
    ::= { slave9Sensor 5}

slave9SensorDoorTwo OBJECT-TYPE
    SYNTAX      DisplayString
    MAX-ACCESS  read-only
    STATUS      current
    DESCRIPTION
	"This is the first device."
    ::= { slave9Sensor 6}	
	
slave9SensorSmoke OBJECT-TYPE
    SYNTAX      DisplayString
    MAX-ACCESS  read-only
    STATUS      current
    DESCRIPTION
	"This is the first device."
    ::= { slave9Sensor 7}
	
slave9SensorWater OBJECT-TYPE
    SYNTAX      DisplayString
    MAX-ACCESS  read-only
    STATUS      current
    DESCRIPTION
	"This is the first device."
    ::= { slave9Sensor 8}
	
slave9SensorTemperatureOneMin OBJECT-TYPE
    SYNTAX      DisplayString
    MAX-ACCESS  read-write
    STATUS      current
    DESCRIPTION
	"This is the first device."
    ::= { slave9Sensor 9}
	
slave9SensorTemperatureOneMinCritical OBJECT-TYPE
    SYNTAX      DisplayString
    MAX-ACCESS  read-write
    STATUS      current
    DESCRIPTION
	"This is the first device."
    ::= { slave9Sensor 10}	
	
slave9SensorTemperatureOneMaxCritical OBJECT-TYPE
    SYNTAX      DisplayString
    MAX-ACCESS  read-write
    STATUS      current
    DESCRIPTION
	"This is the first device."
    ::= { slave9Sensor 11}
	
slave9SensorTemperatureOneMax OBJECT-TYPE
    SYNTAX      DisplayString
    MAX-ACCESS  read-write
    STATUS      current
    DESCRIPTION
	"This is the first device."
    ::= { slave9Sensor 12}

slave9SensorTemperatureTwoMin OBJECT-TYPE
    SYNTAX      DisplayString
    MAX-ACCESS  read-write
    STATUS      current
    DESCRIPTION
	"This is the first device."
    ::= { slave9Sensor 13}
	
slave9SensorTemperatureTwoMinCritical OBJECT-TYPE
    SYNTAX      DisplayString
    MAX-ACCESS  read-write
    STATUS      current
    DESCRIPTION
	"This is the first device."
    ::= { slave9Sensor 14}	
	
slave9SensorTemperatureTwoMaxCritical OBJECT-TYPE
    SYNTAX      DisplayString
    MAX-ACCESS  read-write
    STATUS      current
    DESCRIPTION
	"This is the first device."
    ::= { slave9Sensor 15}
	
slave9SensorTemperatureTwoMax OBJECT-TYPE
    SYNTAX      DisplayString
    MAX-ACCESS  read-write
    STATUS      current
    DESCRIPTION
	"This is the first device."
    ::= { slave9Sensor 16}
	
slave9SensorHumidityOneMin OBJECT-TYPE
    SYNTAX      DisplayString
    MAX-ACCESS  read-write
    STATUS      current
    DESCRIPTION
	"This is the first device."
    ::= { slave9Sensor 17}
	
slave9SensorHumidityOneMinCritical OBJECT-TYPE
    SYNTAX      DisplayString
    MAX-ACCESS  read-write
    STATUS      current
    DESCRIPTION
	"This is the first device."
    ::= { slave9Sensor 18}	
	
slave9SensorHumidityOneMaxCritical OBJECT-TYPE
    SYNTAX      DisplayString
    MAX-ACCESS  read-write
    STATUS      current
    DESCRIPTION
	"This is the first device."
    ::= { slave9Sensor 19}
	
slave9SensorHumidityOneMax OBJECT-TYPE
    SYNTAX      DisplayString
    MAX-ACCESS  read-write
    STATUS      current
    DESCRIPTION
	"This is the first device."
    ::= { slave9Sensor 20}

slave9SensorHumidityTwoMin OBJECT-TYPE
    SYNTAX      DisplayString
    MAX-ACCESS  read-write
    STATUS      current
    DESCRIPTION
	"This is the first device."
    ::= { slave9Sensor 21}
	
slave9SensorHumidityTwoMinCritical OBJECT-TYPE
    SYNTAX      DisplayString
    MAX-ACCESS  read-write
    STATUS      current
    DESCRIPTION
	"This is the first device."
    ::= { slave9Sensor 22}	
	
slave9SensorHumidityTwoMaxCritical OBJECT-TYPE
    SYNTAX      DisplayString
    MAX-ACCESS  read-write
    STATUS      current
    DESCRIPTION
	"This is the first device."
    ::= { slave9Sensor 23}
	
slave9SensorHumidityTwoMax OBJECT-TYPE
    SYNTAX      DisplayString
    MAX-ACCESS  read-write
    STATUS      current
    DESCRIPTION
	"This is the first device."
    ::= { slave9Sensor 24}
	
-------------------------------slave9 output name------------------------	
slave9OutputName OBJECT IDENTIFIER ::= { slave9 5}
slave9OutputNameOne OBJECT-TYPE
    SYNTAX      DisplayString
    MAX-ACCESS  read-write
    STATUS      current
    DESCRIPTION
	"The first output name of slave9"
    ::= { slave9OutputName 1}

slave9OutputNameTwo OBJECT-TYPE
    SYNTAX      DisplayString
    MAX-ACCESS  read-write
    STATUS      current
    DESCRIPTION
	"The second output name of slave9"
    ::= { slave9OutputName 2}

slave9OutputNameThree OBJECT-TYPE
    SYNTAX      DisplayString
    MAX-ACCESS  read-write
    STATUS      current
    DESCRIPTION
	"The second output name of slave9"
    ::= { slave9OutputName 3}

slave9OutputNameFour OBJECT-TYPE
    SYNTAX      DisplayString
    MAX-ACCESS  read-write
    STATUS      current
    DESCRIPTION
	"The second output name of slave9"
    ::= { slave9OutputName 4}

slave9OutputNameFive OBJECT-TYPE
    SYNTAX      DisplayString
    MAX-ACCESS  read-write
    STATUS      current
    DESCRIPTION
	"The second output name of slave9"
    ::= { slave9OutputName 5}

slave9OutputNameSix OBJECT-TYPE
    SYNTAX      DisplayString
    MAX-ACCESS  read-write
    STATUS      current
    DESCRIPTION
	"The second output name of slave9"
    ::= { slave9OutputName 6}

slave9OutputNameSeven OBJECT-TYPE
    SYNTAX      DisplayString
    MAX-ACCESS  read-write
    STATUS      current
    DESCRIPTION
	"The second output name of slave9"
    ::= { slave9OutputName 7}

slave9OutputNameEight OBJECT-TYPE
    SYNTAX      DisplayString
    MAX-ACCESS  read-write
    STATUS      current
    DESCRIPTION
	"The second output name of slave9"
    ::= { slave9OutputName 8}

slave9OutputNameNine OBJECT-TYPE
    SYNTAX      DisplayString
    MAX-ACCESS  read-write
    STATUS      current
    DESCRIPTION
	"The second output name of slave9"
    ::= { slave9OutputName 9}

slave9OutputNameTen OBJECT-TYPE
    SYNTAX      DisplayString
    MAX-ACCESS  read-write
    STATUS      current
    DESCRIPTION
	"The second output name of slave9"
    ::= { slave9OutputName 10}

slave9OutputNameEleven OBJECT-TYPE
    SYNTAX      DisplayString
    MAX-ACCESS  read-write
    STATUS      current
    DESCRIPTION
	"The second output name of slave9"
    ::= { slave9OutputName 11}

slave9OutputNameTwel OBJECT-TYPE
    SYNTAX      DisplayString
    MAX-ACCESS  read-write
    STATUS      current
    DESCRIPTION
	"The second output name of slave9"
    ::= { slave9OutputName 12}

slave9OutputNameThirteen OBJECT-TYPE
    SYNTAX      DisplayString
    MAX-ACCESS  read-write
    STATUS      current
    DESCRIPTION
	"The second output name of slave9"
    ::= { slave9OutputName 13}

slave9OutputNameFourteen OBJECT-TYPE
    SYNTAX      DisplayString
    MAX-ACCESS  read-write
    STATUS      current
    DESCRIPTION
	"The second output name of slave9"
    ::= { slave9OutputName 14}

slave9OutputNameFifteen OBJECT-TYPE
    SYNTAX      DisplayString
    MAX-ACCESS  read-write
    STATUS      current
    DESCRIPTION
	"The second output name of slave9"
    ::= { slave9OutputName 15}

slave9OutputNameSixteen OBJECT-TYPE
    SYNTAX      DisplayString
    MAX-ACCESS  read-write
    STATUS      current
    DESCRIPTION
	"The second output name of slave9"
    ::= { slave9OutputName 16}

slave9OutputNameSeventeen OBJECT-TYPE
    SYNTAX      DisplayString
    MAX-ACCESS  read-write
    STATUS      current
    DESCRIPTION
	"The second output name of slave9"
    ::= { slave9OutputName 17}

slave9OutputNameEighteen OBJECT-TYPE
    SYNTAX      DisplayString
    MAX-ACCESS  read-write
    STATUS      current
    DESCRIPTION
	"The second output name of slave9"
    ::= { slave9OutputName 18}
	
slave9OutputNameNineteen OBJECT-TYPE
    SYNTAX      DisplayString
    MAX-ACCESS  read-write
    STATUS      current
    DESCRIPTION
	"The second output name of slave9"
    ::= { slave9OutputName 19}
	
slave9OutputNametwenty OBJECT-TYPE
    SYNTAX      DisplayString
    MAX-ACCESS  read-write
    STATUS      current
    DESCRIPTION
	"The second output name of slave9"
    ::= { slave9OutputName 20}
	
slave9OutputNameTwentyone OBJECT-TYPE
    SYNTAX      DisplayString
    MAX-ACCESS  read-write
    STATUS      current
    DESCRIPTION
	"The second output name of slave9"
    ::= { slave9OutputName 21}
	
slave9OutputNameTwentyonetwo OBJECT-TYPE
    SYNTAX      DisplayString
    MAX-ACCESS  read-write
    STATUS      current
    DESCRIPTION
	"The second output name of slave9"
    ::= { slave9OutputName 22}
	
slave9OutputNameTwentythree OBJECT-TYPE
    SYNTAX      DisplayString
    MAX-ACCESS  read-write
    STATUS      current
    DESCRIPTION
	"The second output name of slave9"
    ::= { slave9OutputName 23}
	
slave9OutputNameTwentyfour OBJECT-TYPE
    SYNTAX      DisplayString
    MAX-ACCESS  read-write
    STATUS      current
    DESCRIPTION
	"The second output name of slave9"
    ::= { slave9OutputName 24}
	
slave9OutputNameTwentyfive OBJECT-TYPE
    SYNTAX      DisplayString
    MAX-ACCESS  read-write
    STATUS      current
    DESCRIPTION
	"The second output name of slave9"
    ::= { slave9OutputName 25}
	
slave9OutputNameTwentysix OBJECT-TYPE
    SYNTAX      DisplayString
    MAX-ACCESS  read-write
    STATUS      current
    DESCRIPTION
	"The second output name of slave9"
    ::= { slave9OutputName 26}
	
slave9OutputNameTwentyseven OBJECT-TYPE
    SYNTAX      DisplayString
    MAX-ACCESS  read-write
    STATUS      current
    DESCRIPTION
	"The second output name of slave9"
    ::= { slave9OutputName 27}
	
slave9OutputNameTwentyeight OBJECT-TYPE
    SYNTAX      DisplayString
    MAX-ACCESS  read-write
    STATUS      current
    DESCRIPTION
	"The second output name of slave9"
    ::= { slave9OutputName 28}	
slave9OutputNameTwentynine OBJECT-TYPE
    SYNTAX      DisplayString
    MAX-ACCESS  read-write
    STATUS      current
    DESCRIPTION
	"The second output name of slave9"
    ::= { slave9OutputName 29}
	
slave9OutputNameThirty OBJECT-TYPE
    SYNTAX      DisplayString
    MAX-ACCESS  read-write
    STATUS      current
    DESCRIPTION
	"The second output name of slave9"
    ::= { slave9OutputName 30}
	
slave9OutputNameThirtyone OBJECT-TYPE
    SYNTAX      DisplayString
    MAX-ACCESS  read-write
    STATUS      current
    DESCRIPTION
	"The second output name of slave9"
    ::= { slave9OutputName 31}
	
slave9OutputNameThirtytwo OBJECT-TYPE
    SYNTAX      DisplayString
    MAX-ACCESS  read-write
    STATUS      current
    DESCRIPTION
	"The second output name of slave9"
    ::= { slave9OutputName 32}
	
slave9OutputNameThirtythree OBJECT-TYPE
    SYNTAX      DisplayString
    MAX-ACCESS  read-write
    STATUS      current
    DESCRIPTION
	"The second output name of slave9"
    ::= { slave9OutputName 33}
	
slave9OutputNameThirtyfour OBJECT-TYPE
    SYNTAX      DisplayString
    MAX-ACCESS  read-write
    STATUS      current
    DESCRIPTION
	"The second output name of slave9"
    ::= { slave9OutputName 34}
	
slave9OutputNameThirtyfive OBJECT-TYPE
    SYNTAX      DisplayString
    MAX-ACCESS  read-write
    STATUS      current
    DESCRIPTION
	"The second output name of slave9"
    ::= { slave9OutputName 35}
	
slave9OutputNameThirtysix OBJECT-TYPE
    SYNTAX      DisplayString
    MAX-ACCESS  read-write
    STATUS      current
    DESCRIPTION
	"The second output name of slave9"
    ::= { slave9OutputName 36}
	
slave9OutputNameThirtyseven OBJECT-TYPE
    SYNTAX      DisplayString
    MAX-ACCESS  read-write
    STATUS      current
    DESCRIPTION
	"The second output name of slave9"
    ::= { slave9OutputName 37}
	
slave9OutputNameThirtyeight OBJECT-TYPE
    SYNTAX      DisplayString
    MAX-ACCESS  read-write
    STATUS      current
    DESCRIPTION
	"The second output name of slave9"
    ::= { slave9OutputName 38}
	
slave9OutputNameThirtynine OBJECT-TYPE
    SYNTAX      DisplayString
    MAX-ACCESS  read-write
    STATUS      current
    DESCRIPTION
	"The second output name of slave9"
    ::= { slave9OutputName 39}
	
slave9OutputNameFourty OBJECT-TYPE
    SYNTAX      DisplayString
    MAX-ACCESS  read-write
    STATUS      current
    DESCRIPTION
	"The second output name of slave9"
    ::= { slave9OutputName 40}
	
slave9OutputNameFourtyone OBJECT-TYPE
    SYNTAX      DisplayString
    MAX-ACCESS  read-write
    STATUS      current
    DESCRIPTION
	"The second output name of slave9"
    ::= { slave9OutputName 41}
	
slave9OutputNameFourtytwo OBJECT-TYPE
    SYNTAX      DisplayString
    MAX-ACCESS  read-write
    STATUS      current
    DESCRIPTION
	"The second output name of slave9"
    ::= { slave9OutputName 42}	

	
-------------------------------slave9 output delay------------------------	
slave9OutputDelay OBJECT IDENTIFIER ::= { slave9 6}	
slave9OutputDelayOne OBJECT-TYPE
    SYNTAX      DisplayString
    MAX-ACCESS  read-write
    STATUS      current
    DESCRIPTION
	"The first output name of slave9"
    ::= { slave9OutputDelay 1}

slave9OutputDelayTwo OBJECT-TYPE
    SYNTAX      DisplayString
    MAX-ACCESS  read-write
    STATUS      current
    DESCRIPTION
	"The second output name of slave9"
    ::= { slave9OutputDelay 2}

slave9OutputDelayThree OBJECT-TYPE
    SYNTAX      DisplayString
    MAX-ACCESS  read-write
    STATUS      current
    DESCRIPTION
	"The second output name of slave9"
    ::= { slave9OutputDelay 3}

slave9OutputDelayFour OBJECT-TYPE
    SYNTAX      DisplayString
    MAX-ACCESS  read-write
    STATUS      current
    DESCRIPTION
	"The second output name of slave9"
    ::= { slave9OutputDelay 4}

slave9OutputDelayFive OBJECT-TYPE
    SYNTAX      DisplayString
    MAX-ACCESS  read-write
    STATUS      current
    DESCRIPTION
	"The second output name of slave9"
    ::= { slave9OutputDelay 5}

slave9OutputDelaySix OBJECT-TYPE
    SYNTAX      DisplayString
    MAX-ACCESS  read-write
    STATUS      current
    DESCRIPTION
	"The second output name of slave9"
    ::= { slave9OutputDelay 6}

slave9OutputDelaySeven OBJECT-TYPE
    SYNTAX      DisplayString
    MAX-ACCESS  read-write
    STATUS      current
    DESCRIPTION
	"The second output name of slave9"
    ::= { slave9OutputDelay 7}

slave9OutputDelayEight OBJECT-TYPE
    SYNTAX      DisplayString
    MAX-ACCESS  read-write
    STATUS      current
    DESCRIPTION
	"The second output name of slave9"
    ::= { slave9OutputDelay 8}

slave9OutputDelayNine OBJECT-TYPE
    SYNTAX      DisplayString
    MAX-ACCESS  read-write
    STATUS      current
    DESCRIPTION
	"The second output name of slave9"
    ::= { slave9OutputDelay 9}

slave9OutputDelayTen OBJECT-TYPE
    SYNTAX      DisplayString
    MAX-ACCESS  read-write
    STATUS      current
    DESCRIPTION
	"The second output name of slave9"
    ::= { slave9OutputDelay 10}

slave9OutputDelayEleven OBJECT-TYPE
    SYNTAX      DisplayString
    MAX-ACCESS  read-write
    STATUS      current
    DESCRIPTION
	"The second output name of slave9"
    ::= { slave9OutputDelay 11}

slave9OutputDelayTwel OBJECT-TYPE
    SYNTAX      DisplayString
    MAX-ACCESS  read-write
    STATUS      current
    DESCRIPTION
	"The second output name of slave9"
    ::= { slave9OutputDelay 12}

slave9OutputDelayThirteen OBJECT-TYPE
    SYNTAX      DisplayString
    MAX-ACCESS  read-write
    STATUS      current
    DESCRIPTION
	"The second output name of slave9"
    ::= { slave9OutputDelay 13}

slave9OutputDelayFourteen OBJECT-TYPE
    SYNTAX      DisplayString
    MAX-ACCESS  read-write
    STATUS      current
    DESCRIPTION
	"The second output name of slave9"
    ::= { slave9OutputDelay 14}

slave9OutputDelayFifteen OBJECT-TYPE
    SYNTAX      DisplayString
    MAX-ACCESS  read-write
    STATUS      current
    DESCRIPTION
	"The second output name of slave9"
    ::= { slave9OutputDelay 15}

slave9OutputDelaySixteen OBJECT-TYPE
    SYNTAX      DisplayString
    MAX-ACCESS  read-write
    STATUS      current
    DESCRIPTION
	"The second output name of slave9"
    ::= { slave9OutputDelay 16}

slave9OutputDelaySeventeen OBJECT-TYPE
    SYNTAX      DisplayString
    MAX-ACCESS  read-write
    STATUS      current
    DESCRIPTION
	"The second output name of slave9"
    ::= { slave9OutputDelay 17}

slave9OutputDelayEighteen OBJECT-TYPE
    SYNTAX      DisplayString
    MAX-ACCESS  read-write
    STATUS      current
    DESCRIPTION
	"The second output name of slave9"
    ::= { slave9OutputDelay 18}
	
slave9OutputDelayNineteen OBJECT-TYPE
    SYNTAX      DisplayString
    MAX-ACCESS  read-write
    STATUS      current
    DESCRIPTION
	"The second output name of slave9"
    ::= { slave9OutputDelay 19}
	
slave9OutputDelaytwenty OBJECT-TYPE
    SYNTAX      DisplayString
    MAX-ACCESS  read-write
    STATUS      current
    DESCRIPTION
	"The second output name of slave9"
    ::= { slave9OutputDelay 20}
	
slave9OutputDelayTwentyone OBJECT-TYPE
    SYNTAX      DisplayString
    MAX-ACCESS  read-write
    STATUS      current
    DESCRIPTION
	"The second output name of slave9"
    ::= { slave9OutputDelay 21}
	
slave9OutputDelayTwentyonetwo OBJECT-TYPE
    SYNTAX      DisplayString
    MAX-ACCESS  read-write
    STATUS      current
    DESCRIPTION
	"The second output name of slave9"
    ::= { slave9OutputDelay 22}
	
slave9OutputDelayTwentythree OBJECT-TYPE
    SYNTAX      DisplayString
    MAX-ACCESS  read-write
    STATUS      current
    DESCRIPTION
	"The second output name of slave9"
    ::= { slave9OutputDelay 23}
	
slave9OutputDelayTwentyfour OBJECT-TYPE
    SYNTAX      DisplayString
    MAX-ACCESS  read-write
    STATUS      current
    DESCRIPTION
	"The second output name of slave9"
    ::= { slave9OutputDelay 24}
	
slave9OutputDelayTwentyfive OBJECT-TYPE
    SYNTAX      DisplayString
    MAX-ACCESS  read-write
    STATUS      current
    DESCRIPTION
	"The second output name of slave9"
    ::= { slave9OutputDelay 25}
	
slave9OutputDelayTwentysix OBJECT-TYPE
    SYNTAX      DisplayString
    MAX-ACCESS  read-write
    STATUS      current
    DESCRIPTION
	"The second output name of slave9"
    ::= { slave9OutputDelay 26}
	
slave9OutputDelayTwentyseven OBJECT-TYPE
    SYNTAX      DisplayString
    MAX-ACCESS  read-write
    STATUS      current
    DESCRIPTION
	"The second output name of slave9"
    ::= { slave9OutputDelay 27}
	
slave9OutputDelayTwentyeight OBJECT-TYPE
    SYNTAX      DisplayString
    MAX-ACCESS  read-write
    STATUS      current
    DESCRIPTION
	"The second output name of slave9"
    ::= { slave9OutputDelay 28}	
slave9OutputDelayTwentynine OBJECT-TYPE
    SYNTAX      DisplayString
    MAX-ACCESS  read-write
    STATUS      current
    DESCRIPTION
	"The second output name of slave9"
    ::= { slave9OutputDelay 29}
	
slave9OutputDelayThirty OBJECT-TYPE
    SYNTAX      DisplayString
    MAX-ACCESS  read-write
    STATUS      current
    DESCRIPTION
	"The second output name of slave9"
    ::= { slave9OutputDelay 30}
	
slave9OutputDelayThirtyone OBJECT-TYPE
    SYNTAX      DisplayString
    MAX-ACCESS  read-write
    STATUS      current
    DESCRIPTION
	"The second output name of slave9"
    ::= { slave9OutputDelay 31}
	
slave9OutputDelayThirtytwo OBJECT-TYPE
    SYNTAX      DisplayString
    MAX-ACCESS  read-write
    STATUS      current
    DESCRIPTION
	"The second output name of slave9"
    ::= { slave9OutputDelay 32}
	
slave9OutputDelayThirtythree OBJECT-TYPE
    SYNTAX      DisplayString
    MAX-ACCESS  read-write
    STATUS      current
    DESCRIPTION
	"The second output name of slave9"
    ::= { slave9OutputDelay 33}
	
slave9OutputDelayThirtyfour OBJECT-TYPE
    SYNTAX      DisplayString
    MAX-ACCESS  read-write
    STATUS      current
    DESCRIPTION
	"The second output name of slave9"
    ::= { slave9OutputDelay 34}
	
slave9OutputDelayThirtyfive OBJECT-TYPE
    SYNTAX      DisplayString
    MAX-ACCESS  read-write
    STATUS      current
    DESCRIPTION
	"The second output name of slave9"
    ::= { slave9OutputDelay 35}
	
slave9OutputDelayThirtysix OBJECT-TYPE
    SYNTAX      DisplayString
    MAX-ACCESS  read-write
    STATUS      current
    DESCRIPTION
	"The second output name of slave9"
    ::= { slave9OutputDelay 36}
	
slave9OutputDelayThirtyseven OBJECT-TYPE
    SYNTAX      DisplayString
    MAX-ACCESS  read-write
    STATUS      current
    DESCRIPTION
	"The second output name of slave9"
    ::= { slave9OutputDelay 37}
	
slave9OutputDelayThirtyeight OBJECT-TYPE
    SYNTAX      DisplayString
    MAX-ACCESS  read-write
    STATUS      current
    DESCRIPTION
	"The second output name of slave9"
    ::= { slave9OutputDelay 38}
	
slave9OutputDelayThirtynine OBJECT-TYPE
    SYNTAX      DisplayString
    MAX-ACCESS  read-write
    STATUS      current
    DESCRIPTION
	"The second output name of slave9"
    ::= { slave9OutputDelay 39}
	
slave9OutputDelayFourty OBJECT-TYPE
    SYNTAX      DisplayString
    MAX-ACCESS  read-write
    STATUS      current
    DESCRIPTION
	"The second output name of slave9"
    ::= { slave9OutputDelay 40}
	
slave9OutputDelayFourtyone OBJECT-TYPE
    SYNTAX      DisplayString
    MAX-ACCESS  read-write
    STATUS      current
    DESCRIPTION
	"The second output name of slave9"
    ::= { slave9OutputDelay 41}
	
slave9OutputDelayFourtytwo OBJECT-TYPE
    SYNTAX      DisplayString
    MAX-ACCESS  read-write
    STATUS      current
    DESCRIPTION
	"The second output name of slave9"
    ::= { slave9OutputDelay 42}

	
-------------------------------slave9 output switch------------------------	
slave9OutputSwitch OBJECT IDENTIFIER ::= { slave9 7}		
slave9OutputSwitchOne OBJECT-TYPE
    SYNTAX      DisplayString
    MAX-ACCESS  read-write
    STATUS      current
    DESCRIPTION
	"The first output name of slave9"
    ::= { slave9OutputSwitch 1}

slave9OutputSwitchTwo OBJECT-TYPE
    SYNTAX      DisplayString
    MAX-ACCESS  read-write
    STATUS      current
    DESCRIPTION
	"The second output name of slave9"
    ::= { slave9OutputSwitch 2}

slave9OutputSwitchThree OBJECT-TYPE
    SYNTAX      DisplayString
    MAX-ACCESS  read-write
    STATUS      current
    DESCRIPTION
	"The second output name of slave9"
    ::= { slave9OutputSwitch 3}

slave9OutputSwitchFour OBJECT-TYPE
    SYNTAX      DisplayString
    MAX-ACCESS  read-write
    STATUS      current
    DESCRIPTION
	"The second output name of slave9"
    ::= { slave9OutputSwitch 4}

slave9OutputSwitchFive OBJECT-TYPE
    SYNTAX      DisplayString
    MAX-ACCESS  read-write
    STATUS      current
    DESCRIPTION
	"The second output name of slave9"
    ::= { slave9OutputSwitch 5}

slave9OutputSwitchSix OBJECT-TYPE
    SYNTAX      DisplayString
    MAX-ACCESS  read-write
    STATUS      current
    DESCRIPTION
	"The second output name of slave9"
    ::= { slave9OutputSwitch 6}

slave9OutputSwitchSeven OBJECT-TYPE
    SYNTAX      DisplayString
    MAX-ACCESS  read-write
    STATUS      current
    DESCRIPTION
	"The second output name of slave9"
    ::= { slave9OutputSwitch 7}

slave9OutputSwitchEight OBJECT-TYPE
    SYNTAX      DisplayString
    MAX-ACCESS  read-write
    STATUS      current
    DESCRIPTION
	"The second output name of slave9"
    ::= { slave9OutputSwitch 8}

slave9OutputSwitchNine OBJECT-TYPE
    SYNTAX      DisplayString
    MAX-ACCESS  read-write
    STATUS      current
    DESCRIPTION
	"The second output name of slave9"
    ::= { slave9OutputSwitch 9}

slave9OutputSwitchTen OBJECT-TYPE
    SYNTAX      DisplayString
    MAX-ACCESS  read-write
    STATUS      current
    DESCRIPTION
	"The second output name of slave9"
    ::= { slave9OutputSwitch 10}

slave9OutputSwitchEleven OBJECT-TYPE
    SYNTAX      DisplayString
    MAX-ACCESS  read-write
    STATUS      current
    DESCRIPTION
	"The second output name of slave9"
    ::= { slave9OutputSwitch 11}

slave9OutputSwitchTwel OBJECT-TYPE
    SYNTAX      DisplayString
    MAX-ACCESS  read-write
    STATUS      current
    DESCRIPTION
	"The second output name of slave9"
    ::= { slave9OutputSwitch 12}

slave9OutputSwitchThirteen OBJECT-TYPE
    SYNTAX      DisplayString
    MAX-ACCESS  read-write
    STATUS      current
    DESCRIPTION
	"The second output name of slave9"
    ::= { slave9OutputSwitch 13}

slave9OutputSwitchFourteen OBJECT-TYPE
    SYNTAX      DisplayString
    MAX-ACCESS  read-write
    STATUS      current
    DESCRIPTION
	"The second output name of slave9"
    ::= { slave9OutputSwitch 14}

slave9OutputSwitchFifteen OBJECT-TYPE
    SYNTAX      DisplayString
    MAX-ACCESS  read-write
    STATUS      current
    DESCRIPTION
	"The second output name of slave9"
    ::= { slave9OutputSwitch 15}

slave9OutputSwitchSixteen OBJECT-TYPE
    SYNTAX      DisplayString
    MAX-ACCESS  read-write
    STATUS      current
    DESCRIPTION
	"The second output name of slave9"
    ::= { slave9OutputSwitch 16}

slave9OutputSwitchSeventeen OBJECT-TYPE
    SYNTAX      DisplayString
    MAX-ACCESS  read-write
    STATUS      current
    DESCRIPTION
	"The second output name of slave9"
    ::= { slave9OutputSwitch 17}

slave9OutputSwitchEighteen OBJECT-TYPE
    SYNTAX      DisplayString
    MAX-ACCESS  read-write
    STATUS      current
    DESCRIPTION
	"The second output name of slave9"
    ::= { slave9OutputSwitch 18}
	
slave9OutputSwitchNineteen OBJECT-TYPE
    SYNTAX      DisplayString
    MAX-ACCESS  read-write
    STATUS      current
    DESCRIPTION
	"The second output name of slave9"
    ::= { slave9OutputSwitch 19}
	
slave9OutputSwitchtwenty OBJECT-TYPE
    SYNTAX      DisplayString
    MAX-ACCESS  read-write
    STATUS      current
    DESCRIPTION
	"The second output name of slave9"
    ::= { slave9OutputSwitch 20}
	
slave9OutputSwitchTwentyone OBJECT-TYPE
    SYNTAX      DisplayString
    MAX-ACCESS  read-write
    STATUS      current
    DESCRIPTION
	"The second output name of slave9"
    ::= { slave9OutputSwitch 21}
	
slave9OutputSwitchTwentyonetwo OBJECT-TYPE
    SYNTAX      DisplayString
    MAX-ACCESS  read-write
    STATUS      current
    DESCRIPTION
	"The second output name of slave9"
    ::= { slave9OutputSwitch 22}
	
slave9OutputSwitchTwentythree OBJECT-TYPE
    SYNTAX      DisplayString
    MAX-ACCESS  read-write
    STATUS      current
    DESCRIPTION
	"The second output name of slave9"
    ::= { slave9OutputSwitch 23}
	
slave9OutputSwitchTwentyfour OBJECT-TYPE
    SYNTAX      DisplayString
    MAX-ACCESS  read-write
    STATUS      current
    DESCRIPTION
	"The second output name of slave9"
    ::= { slave9OutputSwitch 24}
	
slave9OutputSwitchTwentyfive OBJECT-TYPE
    SYNTAX      DisplayString
    MAX-ACCESS  read-write
    STATUS      current
    DESCRIPTION
	"The second output name of slave9"
    ::= { slave9OutputSwitch 25}
	
slave9OutputSwitchTwentysix OBJECT-TYPE
    SYNTAX      DisplayString
    MAX-ACCESS  read-write
    STATUS      current
    DESCRIPTION
	"The second output name of slave9"
    ::= { slave9OutputSwitch 26}
	
slave9OutputSwitchTwentyseven OBJECT-TYPE
    SYNTAX      DisplayString
    MAX-ACCESS  read-write
    STATUS      current
    DESCRIPTION
	"The second output name of slave9"
    ::= { slave9OutputSwitch 27}
	
slave9OutputSwitchTwentyeight OBJECT-TYPE
    SYNTAX      DisplayString
    MAX-ACCESS  read-write
    STATUS      current
    DESCRIPTION
	"The second output name of slave9"
    ::= { slave9OutputSwitch 28}	
slave9OutputSwitchTwentynine OBJECT-TYPE
    SYNTAX      DisplayString
    MAX-ACCESS  read-write
    STATUS      current
    DESCRIPTION
	"The second output name of slave9"
    ::= { slave9OutputSwitch 29}
	
slave9OutputSwitchThirty OBJECT-TYPE
    SYNTAX      DisplayString
    MAX-ACCESS  read-write
    STATUS      current
    DESCRIPTION
	"The second output name of slave9"
    ::= { slave9OutputSwitch 30}
	
slave9OutputSwitchThirtyone OBJECT-TYPE
    SYNTAX      DisplayString
    MAX-ACCESS  read-write
    STATUS      current
    DESCRIPTION
	"The second output name of slave9"
    ::= { slave9OutputSwitch 31}
	
slave9OutputSwitchThirtytwo OBJECT-TYPE
    SYNTAX      DisplayString
    MAX-ACCESS  read-write
    STATUS      current
    DESCRIPTION
	"The second output name of slave9"
    ::= { slave9OutputSwitch 32}
	
slave9OutputSwitchThirtythree OBJECT-TYPE
    SYNTAX      DisplayString
    MAX-ACCESS  read-write
    STATUS      current
    DESCRIPTION
	"The second output name of slave9"
    ::= { slave9OutputSwitch 33}
	
slave9OutputSwitchThirtyfour OBJECT-TYPE
    SYNTAX      DisplayString
    MAX-ACCESS  read-write
    STATUS      current
    DESCRIPTION
	"The second output name of slave9"
    ::= { slave9OutputSwitch 34}
	
slave9OutputSwitchThirtyfive OBJECT-TYPE
    SYNTAX      DisplayString
    MAX-ACCESS  read-write
    STATUS      current
    DESCRIPTION
	"The second output name of slave9"
    ::= { slave9OutputSwitch 35}
	
slave9OutputSwitchThirtysix OBJECT-TYPE
    SYNTAX      DisplayString
    MAX-ACCESS  read-write
    STATUS      current
    DESCRIPTION
	"The second output name of slave9"
    ::= { slave9OutputSwitch 36}
	
slave9OutputSwitchThirtyseven OBJECT-TYPE
    SYNTAX      DisplayString
    MAX-ACCESS  read-write
    STATUS      current
    DESCRIPTION
	"The second output name of slave9"
    ::= { slave9OutputSwitch 37}
	
slave9OutputSwitchThirtyeight OBJECT-TYPE
    SYNTAX      DisplayString
    MAX-ACCESS  read-write
    STATUS      current
    DESCRIPTION
	"The second output name of slave9"
    ::= { slave9OutputSwitch 38}
	
slave9OutputSwitchThirtynine OBJECT-TYPE
    SYNTAX      DisplayString
    MAX-ACCESS  read-write
    STATUS      current
    DESCRIPTION
	"The second output name of slave9"
    ::= { slave9OutputSwitch 39}
	
slave9OutputSwitchFourty OBJECT-TYPE
    SYNTAX      DisplayString
    MAX-ACCESS  read-write
    STATUS      current
    DESCRIPTION
	"The second output name of slave9"
    ::= { slave9OutputSwitch 40}
	
slave9OutputSwitchFourtyone OBJECT-TYPE
    SYNTAX      DisplayString
    MAX-ACCESS  read-write
    STATUS      current
    DESCRIPTION
	"The second output name of slave9"
    ::= { slave9OutputSwitch 41}
	
slave9OutputSwitchFourtytwo OBJECT-TYPE
    SYNTAX      DisplayString
    MAX-ACCESS  read-write
    STATUS      current
    DESCRIPTION
	"The second output name of slave9"
    ::= { slave9OutputSwitch 42}

	
-------------------------------slave9 output current------------------------	
slave9OutputCurrent OBJECT IDENTIFIER ::= { slave9 8}		
slave9OutputCurrentValue OBJECT IDENTIFIER ::= { slave9OutputCurrent 1}	

slave9OutputCurrentValueOne OBJECT-TYPE
    SYNTAX      DisplayString
    MAX-ACCESS  read-write
    STATUS      current
    DESCRIPTION
	"The first output name of slave9"
    ::= { slave9OutputCurrentValue 1}

slave9OutputCurrentValueTwo OBJECT-TYPE
    SYNTAX      DisplayString
    MAX-ACCESS  read-write
    STATUS      current
    DESCRIPTION
	"The second output name of slave9"
    ::= { slave9OutputCurrentValue 2}

slave9OutputCurrentValueThree OBJECT-TYPE
    SYNTAX      DisplayString
    MAX-ACCESS  read-write
    STATUS      current
    DESCRIPTION
	"The second output name of slave9"
    ::= { slave9OutputCurrentValue 3}

slave9OutputCurrentValueFour OBJECT-TYPE
    SYNTAX      DisplayString
    MAX-ACCESS  read-write
    STATUS      current
    DESCRIPTION
	"The second output name of slave9"
    ::= { slave9OutputCurrentValue 4}

slave9OutputCurrentValueFive OBJECT-TYPE
    SYNTAX      DisplayString
    MAX-ACCESS  read-write
    STATUS      current
    DESCRIPTION
	"The second output name of slave9"
    ::= { slave9OutputCurrentValue 5}

slave9OutputCurrentValueSix OBJECT-TYPE
    SYNTAX      DisplayString
    MAX-ACCESS  read-write
    STATUS      current
    DESCRIPTION
	"The second output name of slave9"
    ::= { slave9OutputCurrentValue 6}

slave9OutputCurrentValueSeven OBJECT-TYPE
    SYNTAX      DisplayString
    MAX-ACCESS  read-write
    STATUS      current
    DESCRIPTION
	"The second output name of slave9"
    ::= { slave9OutputCurrentValue 7}

slave9OutputCurrentValueEight OBJECT-TYPE
    SYNTAX      DisplayString
    MAX-ACCESS  read-write
    STATUS      current
    DESCRIPTION
	"The second output name of slave9"
    ::= { slave9OutputCurrentValue 8}

slave9OutputCurrentValueNine OBJECT-TYPE
    SYNTAX      DisplayString
    MAX-ACCESS  read-write
    STATUS      current
    DESCRIPTION
	"The second output name of slave9"
    ::= { slave9OutputCurrentValue 9}

slave9OutputCurrentValueTen OBJECT-TYPE
    SYNTAX      DisplayString
    MAX-ACCESS  read-write
    STATUS      current
    DESCRIPTION
	"The second output name of slave9"
    ::= { slave9OutputCurrentValue 10}

slave9OutputCurrentValueEleven OBJECT-TYPE
    SYNTAX      DisplayString
    MAX-ACCESS  read-write
    STATUS      current
    DESCRIPTION
	"The second output name of slave9"
    ::= { slave9OutputCurrentValue 11}

slave9OutputCurrentValueTwel OBJECT-TYPE
    SYNTAX      DisplayString
    MAX-ACCESS  read-write
    STATUS      current
    DESCRIPTION
	"The second output name of slave9"
    ::= { slave9OutputCurrentValue 12}

slave9OutputCurrentValueThirteen OBJECT-TYPE
    SYNTAX      DisplayString
    MAX-ACCESS  read-write
    STATUS      current
    DESCRIPTION
	"The second output name of slave9"
    ::= { slave9OutputCurrentValue 13}

slave9OutputCurrentValueFourteen OBJECT-TYPE
    SYNTAX      DisplayString
    MAX-ACCESS  read-write
    STATUS      current
    DESCRIPTION
	"The second output name of slave9"
    ::= { slave9OutputCurrentValue 14}

slave9OutputCurrentValueFifteen OBJECT-TYPE
    SYNTAX      DisplayString
    MAX-ACCESS  read-write
    STATUS      current
    DESCRIPTION
	"The second output name of slave9"
    ::= { slave9OutputCurrentValue 15}

slave9OutputCurrentValueSixteen OBJECT-TYPE
    SYNTAX      DisplayString
    MAX-ACCESS  read-write
    STATUS      current
    DESCRIPTION
	"The second output name of slave9"
    ::= { slave9OutputCurrentValue 16}

slave9OutputCurrentValueSeventeen OBJECT-TYPE
    SYNTAX      DisplayString
    MAX-ACCESS  read-write
    STATUS      current
    DESCRIPTION
	"The second output name of slave9"
    ::= { slave9OutputCurrentValue 17}

slave9OutputCurrentValueEighteen OBJECT-TYPE
    SYNTAX      DisplayString
    MAX-ACCESS  read-write
    STATUS      current
    DESCRIPTION
	"The second output name of slave9"
    ::= { slave9OutputCurrentValue 18}
	
slave9OutputCurrentValueNineteen OBJECT-TYPE
    SYNTAX      DisplayString
    MAX-ACCESS  read-write
    STATUS      current
    DESCRIPTION
	"The second output name of slave9"
    ::= { slave9OutputCurrentValue 19}
	
slave9OutputCurrentValuetwenty OBJECT-TYPE
    SYNTAX      DisplayString
    MAX-ACCESS  read-write
    STATUS      current
    DESCRIPTION
	"The second output name of slave9"
    ::= { slave9OutputCurrentValue 20}
	
slave9OutputCurrentValueTwentyone OBJECT-TYPE
    SYNTAX      DisplayString
    MAX-ACCESS  read-write
    STATUS      current
    DESCRIPTION
	"The second output name of slave9"
    ::= { slave9OutputCurrentValue 21}
	
slave9OutputCurrentValueTwentyonetwo OBJECT-TYPE
    SYNTAX      DisplayString
    MAX-ACCESS  read-write
    STATUS      current
    DESCRIPTION
	"The second output name of slave9"
    ::= { slave9OutputCurrentValue 22}
	
slave9OutputCurrentValueTwentythree OBJECT-TYPE
    SYNTAX      DisplayString
    MAX-ACCESS  read-write
    STATUS      current
    DESCRIPTION
	"The second output name of slave9"
    ::= { slave9OutputCurrentValue 23}
	
slave9OutputCurrentValueTwentyfour OBJECT-TYPE
    SYNTAX      DisplayString
    MAX-ACCESS  read-write
    STATUS      current
    DESCRIPTION
	"The second output name of slave9"
    ::= { slave9OutputCurrentValue 24}
	
slave9OutputCurrentValueTwentyfive OBJECT-TYPE
    SYNTAX      DisplayString
    MAX-ACCESS  read-write
    STATUS      current
    DESCRIPTION
	"The second output name of slave9"
    ::= { slave9OutputCurrentValue 25}
	
slave9OutputCurrentValueTwentysix OBJECT-TYPE
    SYNTAX      DisplayString
    MAX-ACCESS  read-write
    STATUS      current
    DESCRIPTION
	"The second output name of slave9"
    ::= { slave9OutputCurrentValue 26}
	
slave9OutputCurrentValueTwentyseven OBJECT-TYPE
    SYNTAX      DisplayString
    MAX-ACCESS  read-write
    STATUS      current
    DESCRIPTION
	"The second output name of slave9"
    ::= { slave9OutputCurrentValue 27}
	
slave9OutputCurrentValueTwentyeight OBJECT-TYPE
    SYNTAX      DisplayString
    MAX-ACCESS  read-write
    STATUS      current
    DESCRIPTION
	"The second output name of slave9"
    ::= { slave9OutputCurrentValue 28}	
slave9OutputCurrentValueTwentynine OBJECT-TYPE
    SYNTAX      DisplayString
    MAX-ACCESS  read-write
    STATUS      current
    DESCRIPTION
	"The second output name of slave9"
    ::= { slave9OutputCurrentValue 29}
	
slave9OutputCurrentValueThirty OBJECT-TYPE
    SYNTAX      DisplayString
    MAX-ACCESS  read-write
    STATUS      current
    DESCRIPTION
	"The second output name of slave9"
    ::= { slave9OutputCurrentValue 30}
	
slave9OutputCurrentValueThirtyone OBJECT-TYPE
    SYNTAX      DisplayString
    MAX-ACCESS  read-write
    STATUS      current
    DESCRIPTION
	"The second output name of slave9"
    ::= { slave9OutputCurrentValue 31}
	
slave9OutputCurrentValueThirtytwo OBJECT-TYPE
    SYNTAX      DisplayString
    MAX-ACCESS  read-write
    STATUS      current
    DESCRIPTION
	"The second output name of slave9"
    ::= { slave9OutputCurrentValue 32}
	
slave9OutputCurrentValueThirtythree OBJECT-TYPE
    SYNTAX      DisplayString
    MAX-ACCESS  read-write
    STATUS      current
    DESCRIPTION
	"The second output name of slave9"
    ::= { slave9OutputCurrentValue 33}
	
slave9OutputCurrentValueThirtyfour OBJECT-TYPE
    SYNTAX      DisplayString
    MAX-ACCESS  read-write
    STATUS      current
    DESCRIPTION
	"The second output name of slave9"
    ::= { slave9OutputCurrentValue 34}
	
slave9OutputCurrentValueThirtyfive OBJECT-TYPE
    SYNTAX      DisplayString
    MAX-ACCESS  read-write
    STATUS      current
    DESCRIPTION
	"The second output name of slave9"
    ::= { slave9OutputCurrentValue 35}
	
slave9OutputCurrentValueThirtysix OBJECT-TYPE
    SYNTAX      DisplayString
    MAX-ACCESS  read-write
    STATUS      current
    DESCRIPTION
	"The second output name of slave9"
    ::= { slave9OutputCurrentValue 36}
	
slave9OutputCurrentValueThirtyseven OBJECT-TYPE
    SYNTAX      DisplayString
    MAX-ACCESS  read-write
    STATUS      current
    DESCRIPTION
	"The second output name of slave9"
    ::= { slave9OutputCurrentValue 37}
	
slave9OutputCurrentValueThirtyeight OBJECT-TYPE
    SYNTAX      DisplayString
    MAX-ACCESS  read-write
    STATUS      current
    DESCRIPTION
	"The second output name of slave9"
    ::= { slave9OutputCurrentValue 38}
	
slave9OutputCurrentValueThirtynine OBJECT-TYPE
    SYNTAX      DisplayString
    MAX-ACCESS  read-write
    STATUS      current
    DESCRIPTION
	"The second output name of slave9"
    ::= { slave9OutputCurrentValue 39}
	
slave9OutputCurrentValueFourty OBJECT-TYPE
    SYNTAX      DisplayString
    MAX-ACCESS  read-write
    STATUS      current
    DESCRIPTION
	"The second output name of slave9"
    ::= { slave9OutputCurrentValue 40}
	
slave9OutputCurrentValueFourtyone OBJECT-TYPE
    SYNTAX      DisplayString
    MAX-ACCESS  read-write
    STATUS      current
    DESCRIPTION
	"The second output name of slave9"
    ::= { slave9OutputCurrentValue 41}
	
slave9OutputCurrentValueFourtytwo OBJECT-TYPE
    SYNTAX      DisplayString
    MAX-ACCESS  read-write
    STATUS      current
    DESCRIPTION
	"The second output name of slave9"
    ::= { slave9OutputCurrentValue 42}


-------------------------------slave9 output current Min------------------------			
slave9OutputCurrentMin OBJECT IDENTIFIER ::= { slave9OutputCurrent 2}	

slave9OutputCurrentMinOne OBJECT-TYPE
    SYNTAX      DisplayString
    MAX-ACCESS  read-write
    STATUS      current
    DESCRIPTION
	"The first output Min. current alarm value of slave9"
    ::= { slave9OutputCurrentMin 1}

slave9OutputCurrentMinTwo OBJECT-TYPE
    SYNTAX      DisplayString
    MAX-ACCESS  read-write
    STATUS      current
    DESCRIPTION
	"The second output Min. current alarm value of slave9"
    ::= { slave9OutputCurrentMin 2}

slave9OutputCurrentMinThree OBJECT-TYPE
    SYNTAX      DisplayString
    MAX-ACCESS  read-write
    STATUS      current
    DESCRIPTION
	"The second output Min. current alarm value of slave9"
    ::= { slave9OutputCurrentMin 3}

slave9OutputCurrentMinFour OBJECT-TYPE
    SYNTAX      DisplayString
    MAX-ACCESS  read-write
    STATUS      current
    DESCRIPTION
	"The second output Min. current alarm value of slave9"
    ::= { slave9OutputCurrentMin 4}

slave9OutputCurrentMinFive OBJECT-TYPE
    SYNTAX      DisplayString
    MAX-ACCESS  read-write
    STATUS      current
    DESCRIPTION
	"The second output Min. current alarm value of slave9"
    ::= { slave9OutputCurrentMin 5}

slave9OutputCurrentMinSix OBJECT-TYPE
    SYNTAX      DisplayString
    MAX-ACCESS  read-write
    STATUS      current
    DESCRIPTION
	"The second output Min. current alarm value of slave9"
    ::= { slave9OutputCurrentMin 6}

slave9OutputCurrentMinSeven OBJECT-TYPE
    SYNTAX      DisplayString
    MAX-ACCESS  read-write
    STATUS      current
    DESCRIPTION
	"The second output Min. current alarm value of slave9"
    ::= { slave9OutputCurrentMin 7}

slave9OutputCurrentMinEight OBJECT-TYPE
    SYNTAX      DisplayString
    MAX-ACCESS  read-write
    STATUS      current
    DESCRIPTION
	"The second output Min. current alarm value of slave9"
    ::= { slave9OutputCurrentMin 8}

slave9OutputCurrentMinNine OBJECT-TYPE
    SYNTAX      DisplayString
    MAX-ACCESS  read-write
    STATUS      current
    DESCRIPTION
	"The second output Min. current alarm value of slave9"
    ::= { slave9OutputCurrentMin 9}

slave9OutputCurrentMinTen OBJECT-TYPE
    SYNTAX      DisplayString
    MAX-ACCESS  read-write
    STATUS      current
    DESCRIPTION
	"The second output Min. current alarm value of slave9"
    ::= { slave9OutputCurrentMin 10}

slave9OutputCurrentMinEleven OBJECT-TYPE
    SYNTAX      DisplayString
    MAX-ACCESS  read-write
    STATUS      current
    DESCRIPTION
	"The second output Min. current alarm value of slave9"
    ::= { slave9OutputCurrentMin 11}

slave9OutputCurrentMinTwel OBJECT-TYPE
    SYNTAX      DisplayString
    MAX-ACCESS  read-write
    STATUS      current
    DESCRIPTION
	"The second output Min. current alarm value of slave9"
    ::= { slave9OutputCurrentMin 12}

slave9OutputCurrentMinThirteen OBJECT-TYPE
    SYNTAX      DisplayString
    MAX-ACCESS  read-write
    STATUS      current
    DESCRIPTION
	"The second output Min. current alarm value of slave9"
    ::= { slave9OutputCurrentMin 13}

slave9OutputCurrentMinFourteen OBJECT-TYPE
    SYNTAX      DisplayString
    MAX-ACCESS  read-write
    STATUS      current
    DESCRIPTION
	"The second output Min. current alarm value of slave9"
    ::= { slave9OutputCurrentMin 14}

slave9OutputCurrentMinFifteen OBJECT-TYPE
    SYNTAX      DisplayString
    MAX-ACCESS  read-write
    STATUS      current
    DESCRIPTION
	"The second output Min. current alarm value of slave9"
    ::= { slave9OutputCurrentMin 15}

slave9OutputCurrentMinSixteen OBJECT-TYPE
    SYNTAX      DisplayString
    MAX-ACCESS  read-write
    STATUS      current
    DESCRIPTION
	"The second output Min. current alarm value of slave9"
    ::= { slave9OutputCurrentMin 16}

slave9OutputCurrentMinSeventeen OBJECT-TYPE
    SYNTAX      DisplayString
    MAX-ACCESS  read-write
    STATUS      current
    DESCRIPTION
	"The second output Min. current alarm value of slave9"
    ::= { slave9OutputCurrentMin 17}

slave9OutputCurrentMinEighteen OBJECT-TYPE
    SYNTAX      DisplayString
    MAX-ACCESS  read-write
    STATUS      current
    DESCRIPTION
	"The second output Min. current alarm value of slave9"
    ::= { slave9OutputCurrentMin 18}
	
slave9OutputCurrentMinNineteen OBJECT-TYPE
    SYNTAX      DisplayString
    MAX-ACCESS  read-write
    STATUS      current
    DESCRIPTION
	"The second output Min. current alarm value of slave9"
    ::= { slave9OutputCurrentMin 19}
	
slave9OutputCurrentMintwenty OBJECT-TYPE
    SYNTAX      DisplayString
    MAX-ACCESS  read-write
    STATUS      current
    DESCRIPTION
	"The second output Min. current alarm value of slave9"
    ::= { slave9OutputCurrentMin 20}
	
slave9OutputCurrentMinTwentyone OBJECT-TYPE
    SYNTAX      DisplayString
    MAX-ACCESS  read-write
    STATUS      current
    DESCRIPTION
	"The second output Min. current alarm value of slave9"
    ::= { slave9OutputCurrentMin 21}
	
slave9OutputCurrentMinTwentyonetwo OBJECT-TYPE
    SYNTAX      DisplayString
    MAX-ACCESS  read-write
    STATUS      current
    DESCRIPTION
	"The second output Min. current alarm value of slave9"
    ::= { slave9OutputCurrentMin 22}
	
slave9OutputCurrentMinTwentythree OBJECT-TYPE
    SYNTAX      DisplayString
    MAX-ACCESS  read-write
    STATUS      current
    DESCRIPTION
	"The second output Min. current alarm value of slave9"
    ::= { slave9OutputCurrentMin 23}
	
slave9OutputCurrentMinTwentyfour OBJECT-TYPE
    SYNTAX      DisplayString
    MAX-ACCESS  read-write
    STATUS      current
    DESCRIPTION
	"The second output Min. current alarm value of slave9"
    ::= { slave9OutputCurrentMin 24}
	
slave9OutputCurrentMinTwentyfive OBJECT-TYPE
    SYNTAX      DisplayString
    MAX-ACCESS  read-write
    STATUS      current
    DESCRIPTION
	"The second output Min. current alarm value of slave9"
    ::= { slave9OutputCurrentMin 25}
	
slave9OutputCurrentMinTwentysix OBJECT-TYPE
    SYNTAX      DisplayString
    MAX-ACCESS  read-write
    STATUS      current
    DESCRIPTION
	"The second output Min. current alarm value of slave9"
    ::= { slave9OutputCurrentMin 26}
	
slave9OutputCurrentMinTwentyseven OBJECT-TYPE
    SYNTAX      DisplayString
    MAX-ACCESS  read-write
    STATUS      current
    DESCRIPTION
	"The second output Min. current alarm value of slave9"
    ::= { slave9OutputCurrentMin 27}
	
slave9OutputCurrentMinTwentyeight OBJECT-TYPE
    SYNTAX      DisplayString
    MAX-ACCESS  read-write
    STATUS      current
    DESCRIPTION
	"The second output Min. current alarm value of slave9"
    ::= { slave9OutputCurrentMin 28}	
slave9OutputCurrentMinTwentynine OBJECT-TYPE
    SYNTAX      DisplayString
    MAX-ACCESS  read-write
    STATUS      current
    DESCRIPTION
	"The second output Min. current alarm value of slave9"
    ::= { slave9OutputCurrentMin 29}
	
slave9OutputCurrentMinThirty OBJECT-TYPE
    SYNTAX      DisplayString
    MAX-ACCESS  read-write
    STATUS      current
    DESCRIPTION
	"The second output Min. current alarm value of slave9"
    ::= { slave9OutputCurrentMin 30}
	
slave9OutputCurrentMinThirtyone OBJECT-TYPE
    SYNTAX      DisplayString
    MAX-ACCESS  read-write
    STATUS      current
    DESCRIPTION
	"The second output Min. current alarm value of slave9"
    ::= { slave9OutputCurrentMin 31}
	
slave9OutputCurrentMinThirtytwo OBJECT-TYPE
    SYNTAX      DisplayString
    MAX-ACCESS  read-write
    STATUS      current
    DESCRIPTION
	"The second output Min. current alarm value of slave9"
    ::= { slave9OutputCurrentMin 32}
	
slave9OutputCurrentMinThirtythree OBJECT-TYPE
    SYNTAX      DisplayString
    MAX-ACCESS  read-write
    STATUS      current
    DESCRIPTION
	"The second output Min. current alarm value of slave9"
    ::= { slave9OutputCurrentMin 33}
	
slave9OutputCurrentMinThirtyfour OBJECT-TYPE
    SYNTAX      DisplayString
    MAX-ACCESS  read-write
    STATUS      current
    DESCRIPTION
	"The second output Min. current alarm value of slave9"
    ::= { slave9OutputCurrentMin 34}
	
slave9OutputCurrentMinThirtyfive OBJECT-TYPE
    SYNTAX      DisplayString
    MAX-ACCESS  read-write
    STATUS      current
    DESCRIPTION
	"The second output Min. current alarm value of slave9"
    ::= { slave9OutputCurrentMin 35}
	
slave9OutputCurrentMinThirtysix OBJECT-TYPE
    SYNTAX      DisplayString
    MAX-ACCESS  read-write
    STATUS      current
    DESCRIPTION
	"The second output Min. current alarm value of slave9"
    ::= { slave9OutputCurrentMin 36}
	
slave9OutputCurrentMinThirtyseven OBJECT-TYPE
    SYNTAX      DisplayString
    MAX-ACCESS  read-write
    STATUS      current
    DESCRIPTION
	"The second output Min. current alarm value of slave9"
    ::= { slave9OutputCurrentMin 37}
	
slave9OutputCurrentMinThirtyeight OBJECT-TYPE
    SYNTAX      DisplayString
    MAX-ACCESS  read-write
    STATUS      current
    DESCRIPTION
	"The second output Min. current alarm value of slave9"
    ::= { slave9OutputCurrentMin 38}
	
slave9OutputCurrentMinThirtynine OBJECT-TYPE
    SYNTAX      DisplayString
    MAX-ACCESS  read-write
    STATUS      current
    DESCRIPTION
	"The second output Min. current alarm value of slave9"
    ::= { slave9OutputCurrentMin 39}
	
slave9OutputCurrentMinFourty OBJECT-TYPE
    SYNTAX      DisplayString
    MAX-ACCESS  read-write
    STATUS      current
    DESCRIPTION
	"The second output Min. current alarm value of slave9"
    ::= { slave9OutputCurrentMin 40}
	
slave9OutputCurrentMinFourtyone OBJECT-TYPE
    SYNTAX      DisplayString
    MAX-ACCESS  read-write
    STATUS      current
    DESCRIPTION
	"The second output Min. current alarm value of slave9"
    ::= { slave9OutputCurrentMin 41}
	
slave9OutputCurrentMinFourtytwo OBJECT-TYPE
    SYNTAX      DisplayString
    MAX-ACCESS  read-write
    STATUS      current
    DESCRIPTION
	"The second output Min. current alarm value of slave9"
    ::= { slave9OutputCurrentMin 42}


------------------------slave9 output current Min critical----------------			
slave9OutputCurrentMinCritical OBJECT IDENTIFIER ::= { slave9OutputCurrent 3}	

slave9OutputCurrentMinCriticalOne OBJECT-TYPE
    SYNTAX      DisplayString
    MAX-ACCESS  read-write
    STATUS      current
    DESCRIPTION
	"The first output Min. current warning value of slave9"
    ::= { slave9OutputCurrentMinCritical 1}

slave9OutputCurrentMinCriticalTwo OBJECT-TYPE
    SYNTAX      DisplayString
    MAX-ACCESS  read-write
    STATUS      current
    DESCRIPTION
	"The second output Min. current warning value of slave9"
    ::= { slave9OutputCurrentMinCritical 2}

slave9OutputCurrentMinCriticalThree OBJECT-TYPE
    SYNTAX      DisplayString
    MAX-ACCESS  read-write
    STATUS      current
    DESCRIPTION
	"The second output Min. current warning value of slave9"
    ::= { slave9OutputCurrentMinCritical 3}

slave9OutputCurrentMinCriticalFour OBJECT-TYPE
    SYNTAX      DisplayString
    MAX-ACCESS  read-write
    STATUS      current
    DESCRIPTION
	"The second output Min. current warning value of slave9"
    ::= { slave9OutputCurrentMinCritical 4}

slave9OutputCurrentMinCriticalFive OBJECT-TYPE
    SYNTAX      DisplayString
    MAX-ACCESS  read-write
    STATUS      current
    DESCRIPTION
	"The second output Min. current warning value of slave9"
    ::= { slave9OutputCurrentMinCritical 5}

slave9OutputCurrentMinCriticalSix OBJECT-TYPE
    SYNTAX      DisplayString
    MAX-ACCESS  read-write
    STATUS      current
    DESCRIPTION
	"The second output Min. current warning value of slave9"
    ::= { slave9OutputCurrentMinCritical 6}

slave9OutputCurrentMinCriticalSeven OBJECT-TYPE
    SYNTAX      DisplayString
    MAX-ACCESS  read-write
    STATUS      current
    DESCRIPTION
	"The second output Min. current warning value of slave9"
    ::= { slave9OutputCurrentMinCritical 7}

slave9OutputCurrentMinCriticalEight OBJECT-TYPE
    SYNTAX      DisplayString
    MAX-ACCESS  read-write
    STATUS      current
    DESCRIPTION
	"The second output Min. current warning value of slave9"
    ::= { slave9OutputCurrentMinCritical 8}

slave9OutputCurrentMinCriticalNine OBJECT-TYPE
    SYNTAX      DisplayString
    MAX-ACCESS  read-write
    STATUS      current
    DESCRIPTION
	"The second output Min. current warning value of slave9"
    ::= { slave9OutputCurrentMinCritical 9}

slave9OutputCurrentMinCriticalTen OBJECT-TYPE
    SYNTAX      DisplayString
    MAX-ACCESS  read-write
    STATUS      current
    DESCRIPTION
	"The second output Min. current warning value of slave9"
    ::= { slave9OutputCurrentMinCritical 10}

slave9OutputCurrentMinCriticalEleven OBJECT-TYPE
    SYNTAX      DisplayString
    MAX-ACCESS  read-write
    STATUS      current
    DESCRIPTION
	"The second output Min. current warning value of slave9"
    ::= { slave9OutputCurrentMinCritical 11}

slave9OutputCurrentMinCriticalTwel OBJECT-TYPE
    SYNTAX      DisplayString
    MAX-ACCESS  read-write
    STATUS      current
    DESCRIPTION
	"The second output Min. current warning value of slave9"
    ::= { slave9OutputCurrentMinCritical 12}

slave9OutputCurrentMinCriticalThirteen OBJECT-TYPE
    SYNTAX      DisplayString
    MAX-ACCESS  read-write
    STATUS      current
    DESCRIPTION
	"The second output Min. current warning value of slave9"
    ::= { slave9OutputCurrentMinCritical 13}

slave9OutputCurrentMinCriticalFourteen OBJECT-TYPE
    SYNTAX      DisplayString
    MAX-ACCESS  read-write
    STATUS      current
    DESCRIPTION
	"The second output Min. current warning value of slave9"
    ::= { slave9OutputCurrentMinCritical 14}

slave9OutputCurrentMinCriticalFifteen OBJECT-TYPE
    SYNTAX      DisplayString
    MAX-ACCESS  read-write
    STATUS      current
    DESCRIPTION
	"The second output Min. current warning value of slave9"
    ::= { slave9OutputCurrentMinCritical 15}

slave9OutputCurrentMinCriticalSixteen OBJECT-TYPE
    SYNTAX      DisplayString
    MAX-ACCESS  read-write
    STATUS      current
    DESCRIPTION
	"The second output Min. current warning value of slave9"
    ::= { slave9OutputCurrentMinCritical 16}

slave9OutputCurrentMinCriticalSeventeen OBJECT-TYPE
    SYNTAX      DisplayString
    MAX-ACCESS  read-write
    STATUS      current
    DESCRIPTION
	"The second output Min. current warning value of slave9"
    ::= { slave9OutputCurrentMinCritical 17}

slave9OutputCurrentMinCriticalEighteen OBJECT-TYPE
    SYNTAX      DisplayString
    MAX-ACCESS  read-write
    STATUS      current
    DESCRIPTION
	"The second output Min. current warning value of slave9"
    ::= { slave9OutputCurrentMinCritical 18}
	
slave9OutputCurrentMinCriticalNineteen OBJECT-TYPE
    SYNTAX      DisplayString
    MAX-ACCESS  read-write
    STATUS      current
    DESCRIPTION
	"The second output Min. current warning value of slave9"
    ::= { slave9OutputCurrentMinCritical 19}
	
slave9OutputCurrentMinCriticaltwenty OBJECT-TYPE
    SYNTAX      DisplayString
    MAX-ACCESS  read-write
    STATUS      current
    DESCRIPTION
	"The second output Min. current warning value of slave9"
    ::= { slave9OutputCurrentMinCritical 20}
	
slave9OutputCurrentMinCriticalTwentyone OBJECT-TYPE
    SYNTAX      DisplayString
    MAX-ACCESS  read-write
    STATUS      current
    DESCRIPTION
	"The second output Min. current warning value of slave9"
    ::= { slave9OutputCurrentMinCritical 21}
	
slave9OutputCurrentMinCriticalTwentyonetwo OBJECT-TYPE
    SYNTAX      DisplayString
    MAX-ACCESS  read-write
    STATUS      current
    DESCRIPTION
	"The second output Min. current warning value of slave9"
    ::= { slave9OutputCurrentMinCritical 22}
	
slave9OutputCurrentMinCriticalTwentythree OBJECT-TYPE
    SYNTAX      DisplayString
    MAX-ACCESS  read-write
    STATUS      current
    DESCRIPTION
	"The second output Min. current warning value of slave9"
    ::= { slave9OutputCurrentMinCritical 23}
	
slave9OutputCurrentMinCriticalTwentyfour OBJECT-TYPE
    SYNTAX      DisplayString
    MAX-ACCESS  read-write
    STATUS      current
    DESCRIPTION
	"The second output Min. current warning value of slave9"
    ::= { slave9OutputCurrentMinCritical 24}
	
slave9OutputCurrentMinCriticalTwentyfive OBJECT-TYPE
    SYNTAX      DisplayString
    MAX-ACCESS  read-write
    STATUS      current
    DESCRIPTION
	"The second output Min. current warning value of slave9"
    ::= { slave9OutputCurrentMinCritical 25}
	
slave9OutputCurrentMinCriticalTwentysix OBJECT-TYPE
    SYNTAX      DisplayString
    MAX-ACCESS  read-write
    STATUS      current
    DESCRIPTION
	"The second output Min. current warning value of slave9"
    ::= { slave9OutputCurrentMinCritical 26}
	
slave9OutputCurrentMinCriticalTwentyseven OBJECT-TYPE
    SYNTAX      DisplayString
    MAX-ACCESS  read-write
    STATUS      current
    DESCRIPTION
	"The second output Min. current warning value of slave9"
    ::= { slave9OutputCurrentMinCritical 27}
	
slave9OutputCurrentMinCriticalTwentyeight OBJECT-TYPE
    SYNTAX      DisplayString
    MAX-ACCESS  read-write
    STATUS      current
    DESCRIPTION
	"The second output Min. current warning value of slave9"
    ::= { slave9OutputCurrentMinCritical 28}	
slave9OutputCurrentMinCriticalTwentynine OBJECT-TYPE
    SYNTAX      DisplayString
    MAX-ACCESS  read-write
    STATUS      current
    DESCRIPTION
	"The second output Min. current warning value of slave9"
    ::= { slave9OutputCurrentMinCritical 29}
	
slave9OutputCurrentMinCriticalThirty OBJECT-TYPE
    SYNTAX      DisplayString
    MAX-ACCESS  read-write
    STATUS      current
    DESCRIPTION
	"The second output Min. current warning value of slave9"
    ::= { slave9OutputCurrentMinCritical 30}
	
slave9OutputCurrentMinCriticalThirtyone OBJECT-TYPE
    SYNTAX      DisplayString
    MAX-ACCESS  read-write
    STATUS      current
    DESCRIPTION
	"The second output Min. current warning value of slave9"
    ::= { slave9OutputCurrentMinCritical 31}
	
slave9OutputCurrentMinCriticalThirtytwo OBJECT-TYPE
    SYNTAX      DisplayString
    MAX-ACCESS  read-write
    STATUS      current
    DESCRIPTION
	"The second output Min. current warning value of slave9"
    ::= { slave9OutputCurrentMinCritical 32}
	
slave9OutputCurrentMinCriticalThirtythree OBJECT-TYPE
    SYNTAX      DisplayString
    MAX-ACCESS  read-write
    STATUS      current
    DESCRIPTION
	"The second output Min. current warning value of slave9"
    ::= { slave9OutputCurrentMinCritical 33}
	
slave9OutputCurrentMinCriticalThirtyfour OBJECT-TYPE
    SYNTAX      DisplayString
    MAX-ACCESS  read-write
    STATUS      current
    DESCRIPTION
	"The second output Min. current warning value of slave9"
    ::= { slave9OutputCurrentMinCritical 34}
	
slave9OutputCurrentMinCriticalThirtyfive OBJECT-TYPE
    SYNTAX      DisplayString
    MAX-ACCESS  read-write
    STATUS      current
    DESCRIPTION
	"The second output Min. current warning value of slave9"
    ::= { slave9OutputCurrentMinCritical 35}
	
slave9OutputCurrentMinCriticalThirtysix OBJECT-TYPE
    SYNTAX      DisplayString
    MAX-ACCESS  read-write
    STATUS      current
    DESCRIPTION
	"The second output Min. current warning value of slave9"
    ::= { slave9OutputCurrentMinCritical 36}
	
slave9OutputCurrentMinCriticalThirtyseven OBJECT-TYPE
    SYNTAX      DisplayString
    MAX-ACCESS  read-write
    STATUS      current
    DESCRIPTION
	"The second output Min. current warning value of slave9"
    ::= { slave9OutputCurrentMinCritical 37}
	
slave9OutputCurrentMinCriticalThirtyeight OBJECT-TYPE
    SYNTAX      DisplayString
    MAX-ACCESS  read-write
    STATUS      current
    DESCRIPTION
	"The second output Min. current warning value of slave9"
    ::= { slave9OutputCurrentMinCritical 38}
	
slave9OutputCurrentMinCriticalThirtynine OBJECT-TYPE
    SYNTAX      DisplayString
    MAX-ACCESS  read-write
    STATUS      current
    DESCRIPTION
	"The second output Min. current warning value of slave9"
    ::= { slave9OutputCurrentMinCritical 39}
	
slave9OutputCurrentMinCriticalFourty OBJECT-TYPE
    SYNTAX      DisplayString
    MAX-ACCESS  read-write
    STATUS      current
    DESCRIPTION
	"The second output Min. current warning value of slave9"
    ::= { slave9OutputCurrentMinCritical 40}
	
slave9OutputCurrentMinCriticalFourtyone OBJECT-TYPE
    SYNTAX      DisplayString
    MAX-ACCESS  read-write
    STATUS      current
    DESCRIPTION
	"The second output Min. current warning value of slave9"
    ::= { slave9OutputCurrentMinCritical 41}
	
slave9OutputCurrentMinCriticalFourtytwo OBJECT-TYPE
    SYNTAX      DisplayString
    MAX-ACCESS  read-write
    STATUS      current
    DESCRIPTION
	"The second output Min. current warning value of slave9"
    ::= { slave9OutputCurrentMinCritical 42}
	
	
------------------------slave9 output current Max critical----------------			
slave9OutputCurrentMaxCritical OBJECT IDENTIFIER ::= { slave9OutputCurrent 4}	

slave9OutputCurrentMaxCriticalOne OBJECT-TYPE
    SYNTAX      DisplayString
    MAX-ACCESS  read-write
    STATUS      current
    DESCRIPTION
	"The first output Max. current warning value of slave9"
    ::= { slave9OutputCurrentMaxCritical 1}

slave9OutputCurrentMaxCriticalTwo OBJECT-TYPE
    SYNTAX      DisplayString
    MAX-ACCESS  read-write
    STATUS      current
    DESCRIPTION
	"The second output Max. current warning value of slave9"
    ::= { slave9OutputCurrentMaxCritical 2}

slave9OutputCurrentMaxCriticalThree OBJECT-TYPE
    SYNTAX      DisplayString
    MAX-ACCESS  read-write
    STATUS      current
    DESCRIPTION
	"The second output Max. current warning value of slave9"
    ::= { slave9OutputCurrentMaxCritical 3}

slave9OutputCurrentMaxCriticalFour OBJECT-TYPE
    SYNTAX      DisplayString
    MAX-ACCESS  read-write
    STATUS      current
    DESCRIPTION
	"The second output Max. current warning value of slave9"
    ::= { slave9OutputCurrentMaxCritical 4}

slave9OutputCurrentMaxCriticalFive OBJECT-TYPE
    SYNTAX      DisplayString
    MAX-ACCESS  read-write
    STATUS      current
    DESCRIPTION
	"The second output Max. current warning value of slave9"
    ::= { slave9OutputCurrentMaxCritical 5}

slave9OutputCurrentMaxCriticalSix OBJECT-TYPE
    SYNTAX      DisplayString
    MAX-ACCESS  read-write
    STATUS      current
    DESCRIPTION
	"The second output Max. current warning value of slave9"
    ::= { slave9OutputCurrentMaxCritical 6}

slave9OutputCurrentMaxCriticalSeven OBJECT-TYPE
    SYNTAX      DisplayString
    MAX-ACCESS  read-write
    STATUS      current
    DESCRIPTION
	"The second output Max. current warning value of slave9"
    ::= { slave9OutputCurrentMaxCritical 7}

slave9OutputCurrentMaxCriticalEight OBJECT-TYPE
    SYNTAX      DisplayString
    MAX-ACCESS  read-write
    STATUS      current
    DESCRIPTION
	"The second output Max. current warning value of slave9"
    ::= { slave9OutputCurrentMaxCritical 8}

slave9OutputCurrentMaxCriticalNine OBJECT-TYPE
    SYNTAX      DisplayString
    MAX-ACCESS  read-write
    STATUS      current
    DESCRIPTION
	"The second output Max. current warning value of slave9"
    ::= { slave9OutputCurrentMaxCritical 9}

slave9OutputCurrentMaxCriticalTen OBJECT-TYPE
    SYNTAX      DisplayString
    MAX-ACCESS  read-write
    STATUS      current
    DESCRIPTION
	"The second output Max. current warning value of slave9"
    ::= { slave9OutputCurrentMaxCritical 10}

slave9OutputCurrentMaxCriticalEleven OBJECT-TYPE
    SYNTAX      DisplayString
    MAX-ACCESS  read-write
    STATUS      current
    DESCRIPTION
	"The second output Max. current warning value of slave9"
    ::= { slave9OutputCurrentMaxCritical 11}

slave9OutputCurrentMaxCriticalTwel OBJECT-TYPE
    SYNTAX      DisplayString
    MAX-ACCESS  read-write
    STATUS      current
    DESCRIPTION
	"The second output Max. current warning value of slave9"
    ::= { slave9OutputCurrentMaxCritical 12}

slave9OutputCurrentMaxCriticalThirteen OBJECT-TYPE
    SYNTAX      DisplayString
    MAX-ACCESS  read-write
    STATUS      current
    DESCRIPTION
	"The second output Max. current warning value of slave9"
    ::= { slave9OutputCurrentMaxCritical 13}

slave9OutputCurrentMaxCriticalFourteen OBJECT-TYPE
    SYNTAX      DisplayString
    MAX-ACCESS  read-write
    STATUS      current
    DESCRIPTION
	"The second output Max. current warning value of slave9"
    ::= { slave9OutputCurrentMaxCritical 14}

slave9OutputCurrentMaxCriticalFifteen OBJECT-TYPE
    SYNTAX      DisplayString
    MAX-ACCESS  read-write
    STATUS      current
    DESCRIPTION
	"The second output Max. current warning value of slave9"
    ::= { slave9OutputCurrentMaxCritical 15}

slave9OutputCurrentMaxCriticalSixteen OBJECT-TYPE
    SYNTAX      DisplayString
    MAX-ACCESS  read-write
    STATUS      current
    DESCRIPTION
	"The second output Max. current warning value of slave9"
    ::= { slave9OutputCurrentMaxCritical 16}

slave9OutputCurrentMaxCriticalSeventeen OBJECT-TYPE
    SYNTAX      DisplayString
    MAX-ACCESS  read-write
    STATUS      current
    DESCRIPTION
	"The second output Max. current warning value of slave9"
    ::= { slave9OutputCurrentMaxCritical 17}

slave9OutputCurrentMaxCriticalEighteen OBJECT-TYPE
    SYNTAX      DisplayString
    MAX-ACCESS  read-write
    STATUS      current
    DESCRIPTION
	"The second output Max. current warning value of slave9"
    ::= { slave9OutputCurrentMaxCritical 18}
	
slave9OutputCurrentMaxCriticalNineteen OBJECT-TYPE
    SYNTAX      DisplayString
    MAX-ACCESS  read-write
    STATUS      current
    DESCRIPTION
	"The second output Max. current warning value of slave9"
    ::= { slave9OutputCurrentMaxCritical 19}
	
slave9OutputCurrentMaxCriticaltwenty OBJECT-TYPE
    SYNTAX      DisplayString
    MAX-ACCESS  read-write
    STATUS      current
    DESCRIPTION
	"The second output Max. current warning value of slave9"
    ::= { slave9OutputCurrentMaxCritical 20}
	
slave9OutputCurrentMaxCriticalTwentyone OBJECT-TYPE
    SYNTAX      DisplayString
    MAX-ACCESS  read-write
    STATUS      current
    DESCRIPTION
	"The second output Max. current warning value of slave9"
    ::= { slave9OutputCurrentMaxCritical 21}
	
slave9OutputCurrentMaxCriticalTwentyonetwo OBJECT-TYPE
    SYNTAX      DisplayString
    MAX-ACCESS  read-write
    STATUS      current
    DESCRIPTION
	"The second output Max. current warning value of slave9"
    ::= { slave9OutputCurrentMaxCritical 22}
	
slave9OutputCurrentMaxCriticalTwentythree OBJECT-TYPE
    SYNTAX      DisplayString
    MAX-ACCESS  read-write
    STATUS      current
    DESCRIPTION
	"The second output Max. current warning value of slave9"
    ::= { slave9OutputCurrentMaxCritical 23}
	
slave9OutputCurrentMaxCriticalTwentyfour OBJECT-TYPE
    SYNTAX      DisplayString
    MAX-ACCESS  read-write
    STATUS      current
    DESCRIPTION
	"The second output Max. current warning value of slave9"
    ::= { slave9OutputCurrentMaxCritical 24}
	
slave9OutputCurrentMaxCriticalTwentyfive OBJECT-TYPE
    SYNTAX      DisplayString
    MAX-ACCESS  read-write
    STATUS      current
    DESCRIPTION
	"The second output Max. current warning value of slave9"
    ::= { slave9OutputCurrentMaxCritical 25}
	
slave9OutputCurrentMaxCriticalTwentysix OBJECT-TYPE
    SYNTAX      DisplayString
    MAX-ACCESS  read-write
    STATUS      current
    DESCRIPTION
	"The second output Max. current warning value of slave9"
    ::= { slave9OutputCurrentMaxCritical 26}
	
slave9OutputCurrentMaxCriticalTwentyseven OBJECT-TYPE
    SYNTAX      DisplayString
    MAX-ACCESS  read-write
    STATUS      current
    DESCRIPTION
	"The second output Max. current warning value of slave9"
    ::= { slave9OutputCurrentMaxCritical 27}
	
slave9OutputCurrentMaxCriticalTwentyeight OBJECT-TYPE
    SYNTAX      DisplayString
    MAX-ACCESS  read-write
    STATUS      current
    DESCRIPTION
	"The second output Max. current warning value of slave9"
    ::= { slave9OutputCurrentMaxCritical 28}	
slave9OutputCurrentMaxCriticalTwentynine OBJECT-TYPE
    SYNTAX      DisplayString
    MAX-ACCESS  read-write
    STATUS      current
    DESCRIPTION
	"The second output Max. current warning value of slave9"
    ::= { slave9OutputCurrentMaxCritical 29}
	
slave9OutputCurrentMaxCriticalThirty OBJECT-TYPE
    SYNTAX      DisplayString
    MAX-ACCESS  read-write
    STATUS      current
    DESCRIPTION
	"The second output Max. current warning value of slave9"
    ::= { slave9OutputCurrentMaxCritical 30}
	
slave9OutputCurrentMaxCriticalThirtyone OBJECT-TYPE
    SYNTAX      DisplayString
    MAX-ACCESS  read-write
    STATUS      current
    DESCRIPTION
	"The second output Max. current warning value of slave9"
    ::= { slave9OutputCurrentMaxCritical 31}
	
slave9OutputCurrentMaxCriticalThirtytwo OBJECT-TYPE
    SYNTAX      DisplayString
    MAX-ACCESS  read-write
    STATUS      current
    DESCRIPTION
	"The second output Max. current warning value of slave9"
    ::= { slave9OutputCurrentMaxCritical 32}
	
slave9OutputCurrentMaxCriticalThirtythree OBJECT-TYPE
    SYNTAX      DisplayString
    MAX-ACCESS  read-write
    STATUS      current
    DESCRIPTION
	"The second output Max. current warning value of slave9"
    ::= { slave9OutputCurrentMaxCritical 33}
	
slave9OutputCurrentMaxCriticalThirtyfour OBJECT-TYPE
    SYNTAX      DisplayString
    MAX-ACCESS  read-write
    STATUS      current
    DESCRIPTION
	"The second output Max. current warning value of slave9"
    ::= { slave9OutputCurrentMaxCritical 34}
	
slave9OutputCurrentMaxCriticalThirtyfive OBJECT-TYPE
    SYNTAX      DisplayString
    MAX-ACCESS  read-write
    STATUS      current
    DESCRIPTION
	"The second output Max. current warning value of slave9"
    ::= { slave9OutputCurrentMaxCritical 35}
	
slave9OutputCurrentMaxCriticalThirtysix OBJECT-TYPE
    SYNTAX      DisplayString
    MAX-ACCESS  read-write
    STATUS      current
    DESCRIPTION
	"The second output Max. current warning value of slave9"
    ::= { slave9OutputCurrentMaxCritical 36}
	
slave9OutputCurrentMaxCriticalThirtyseven OBJECT-TYPE
    SYNTAX      DisplayString
    MAX-ACCESS  read-write
    STATUS      current
    DESCRIPTION
	"The second output Max. current warning value of slave9"
    ::= { slave9OutputCurrentMaxCritical 37}
	
slave9OutputCurrentMaxCriticalThirtyeight OBJECT-TYPE
    SYNTAX      DisplayString
    MAX-ACCESS  read-write
    STATUS      current
    DESCRIPTION
	"The second output Max. current warning value of slave9"
    ::= { slave9OutputCurrentMaxCritical 38}
	
slave9OutputCurrentMaxCriticalThirtynine OBJECT-TYPE
    SYNTAX      DisplayString
    MAX-ACCESS  read-write
    STATUS      current
    DESCRIPTION
	"The second output Max. current warning value of slave9"
    ::= { slave9OutputCurrentMaxCritical 39}
	
slave9OutputCurrentMaxCriticalFourty OBJECT-TYPE
    SYNTAX      DisplayString
    MAX-ACCESS  read-write
    STATUS      current
    DESCRIPTION
	"The second output Max. current warning value of slave9"
    ::= { slave9OutputCurrentMaxCritical 40}
	
slave9OutputCurrentMaxCriticalFourtyone OBJECT-TYPE
    SYNTAX      DisplayString
    MAX-ACCESS  read-write
    STATUS      current
    DESCRIPTION
	"The second output Max. current warning value of slave9"
    ::= { slave9OutputCurrentMaxCritical 41}
	
slave9OutputCurrentMaxCriticalFourtytwo OBJECT-TYPE
    SYNTAX      DisplayString
    MAX-ACCESS  read-write
    STATUS      current
    DESCRIPTION
	"The second output Max. current warning value of slave9"
    ::= { slave9OutputCurrentMaxCritical 42}
	
	
------------------------slave9 output current Max----------------			
slave9OutputCurrentMax OBJECT IDENTIFIER ::= { slave9OutputCurrent 5}
	
slave9OutputCurrentMaxOne OBJECT-TYPE
    SYNTAX      DisplayString
    MAX-ACCESS  read-write
    STATUS      current
    DESCRIPTION
	"The first output Max. current alarm value of slave9"
    ::= { slave9OutputCurrentMax 1}

slave9OutputCurrentMaxTwo OBJECT-TYPE
    SYNTAX      DisplayString
    MAX-ACCESS  read-write
    STATUS      current
    DESCRIPTION
	"The second output Max. current alarm value of slave9"
    ::= { slave9OutputCurrentMax 2}

slave9OutputCurrentMaxThree OBJECT-TYPE
    SYNTAX      DisplayString
    MAX-ACCESS  read-write
    STATUS      current
    DESCRIPTION
	"The second output Max. current alarm value of slave9"
    ::= { slave9OutputCurrentMax 3}

slave9OutputCurrentMaxFour OBJECT-TYPE
    SYNTAX      DisplayString
    MAX-ACCESS  read-write
    STATUS      current
    DESCRIPTION
	"The second output Max. current alarm value of slave9"
    ::= { slave9OutputCurrentMax 4}

slave9OutputCurrentMaxFive OBJECT-TYPE
    SYNTAX      DisplayString
    MAX-ACCESS  read-write
    STATUS      current
    DESCRIPTION
	"The second output Max. current alarm value of slave9"
    ::= { slave9OutputCurrentMax 5}

slave9OutputCurrentMaxSix OBJECT-TYPE
    SYNTAX      DisplayString
    MAX-ACCESS  read-write
    STATUS      current
    DESCRIPTION
	"The second output Max. current alarm value of slave9"
    ::= { slave9OutputCurrentMax 6}

slave9OutputCurrentMaxSeven OBJECT-TYPE
    SYNTAX      DisplayString
    MAX-ACCESS  read-write
    STATUS      current
    DESCRIPTION
	"The second output Max. current alarm value of slave9"
    ::= { slave9OutputCurrentMax 7}

slave9OutputCurrentMaxEight OBJECT-TYPE
    SYNTAX      DisplayString
    MAX-ACCESS  read-write
    STATUS      current
    DESCRIPTION
	"The second output Max. current alarm value of slave9"
    ::= { slave9OutputCurrentMax 8}

slave9OutputCurrentMaxNine OBJECT-TYPE
    SYNTAX      DisplayString
    MAX-ACCESS  read-write
    STATUS      current
    DESCRIPTION
	"The second output Max. current alarm value of slave9"
    ::= { slave9OutputCurrentMax 9}

slave9OutputCurrentMaxTen OBJECT-TYPE
    SYNTAX      DisplayString
    MAX-ACCESS  read-write
    STATUS      current
    DESCRIPTION
	"The second output Max. current alarm value of slave9"
    ::= { slave9OutputCurrentMax 10}

slave9OutputCurrentMaxEleven OBJECT-TYPE
    SYNTAX      DisplayString
    MAX-ACCESS  read-write
    STATUS      current
    DESCRIPTION
	"The second output Max. current alarm value of slave9"
    ::= { slave9OutputCurrentMax 11}

slave9OutputCurrentMaxTwel OBJECT-TYPE
    SYNTAX      DisplayString
    MAX-ACCESS  read-write
    STATUS      current
    DESCRIPTION
	"The second output Max. current alarm value of slave9"
    ::= { slave9OutputCurrentMax 12}

slave9OutputCurrentMaxThirteen OBJECT-TYPE
    SYNTAX      DisplayString
    MAX-ACCESS  read-write
    STATUS      current
    DESCRIPTION
	"The second output Max. current alarm value of slave9"
    ::= { slave9OutputCurrentMax 13}

slave9OutputCurrentMaxFourteen OBJECT-TYPE
    SYNTAX      DisplayString
    MAX-ACCESS  read-write
    STATUS      current
    DESCRIPTION
	"The second output Max. current alarm value of slave9"
    ::= { slave9OutputCurrentMax 14}

slave9OutputCurrentMaxFifteen OBJECT-TYPE
    SYNTAX      DisplayString
    MAX-ACCESS  read-write
    STATUS      current
    DESCRIPTION
	"The second output Max. current alarm value of slave9"
    ::= { slave9OutputCurrentMax 15}

slave9OutputCurrentMaxSixteen OBJECT-TYPE
    SYNTAX      DisplayString
    MAX-ACCESS  read-write
    STATUS      current
    DESCRIPTION
	"The second output Max. current alarm value of slave9"
    ::= { slave9OutputCurrentMax 16}

slave9OutputCurrentMaxSeventeen OBJECT-TYPE
    SYNTAX      DisplayString
    MAX-ACCESS  read-write
    STATUS      current
    DESCRIPTION
	"The second output Max. current alarm value of slave9"
    ::= { slave9OutputCurrentMax 17}

slave9OutputCurrentMaxEighteen OBJECT-TYPE
    SYNTAX      DisplayString
    MAX-ACCESS  read-write
    STATUS      current
    DESCRIPTION
	"The second output Max. current alarm value of slave9"
    ::= { slave9OutputCurrentMax 18}
	
slave9OutputCurrentMaxNineteen OBJECT-TYPE
    SYNTAX      DisplayString
    MAX-ACCESS  read-write
    STATUS      current
    DESCRIPTION
	"The second output Max. current alarm value of slave9"
    ::= { slave9OutputCurrentMax 19}
	
slave9OutputCurrentMaxtwenty OBJECT-TYPE
    SYNTAX      DisplayString
    MAX-ACCESS  read-write
    STATUS      current
    DESCRIPTION
	"The second output Max. current alarm value of slave9"
    ::= { slave9OutputCurrentMax 20}
	
slave9OutputCurrentMaxTwentyone OBJECT-TYPE
    SYNTAX      DisplayString
    MAX-ACCESS  read-write
    STATUS      current
    DESCRIPTION
	"The second output Max. current alarm value of slave9"
    ::= { slave9OutputCurrentMax 21}
	
slave9OutputCurrentMaxTwentyonetwo OBJECT-TYPE
    SYNTAX      DisplayString
    MAX-ACCESS  read-write
    STATUS      current
    DESCRIPTION
	"The second output Max. current alarm value of slave9"
    ::= { slave9OutputCurrentMax 22}
	
slave9OutputCurrentMaxTwentythree OBJECT-TYPE
    SYNTAX      DisplayString
    MAX-ACCESS  read-write
    STATUS      current
    DESCRIPTION
	"The second output Max. current alarm value of slave9"
    ::= { slave9OutputCurrentMax 23}
	
slave9OutputCurrentMaxTwentyfour OBJECT-TYPE
    SYNTAX      DisplayString
    MAX-ACCESS  read-write
    STATUS      current
    DESCRIPTION
	"The second output Max. current alarm value of slave9"
    ::= { slave9OutputCurrentMax 24}
	
slave9OutputCurrentMaxTwentyfive OBJECT-TYPE
    SYNTAX      DisplayString
    MAX-ACCESS  read-write
    STATUS      current
    DESCRIPTION
	"The second output Max. current alarm value of slave9"
    ::= { slave9OutputCurrentMax 25}
	
slave9OutputCurrentMaxTwentysix OBJECT-TYPE
    SYNTAX      DisplayString
    MAX-ACCESS  read-write
    STATUS      current
    DESCRIPTION
	"The second output Max. current alarm value of slave9"
    ::= { slave9OutputCurrentMax 26}
	
slave9OutputCurrentMaxTwentyseven OBJECT-TYPE
    SYNTAX      DisplayString
    MAX-ACCESS  read-write
    STATUS      current
    DESCRIPTION
	"The second output Max. current alarm value of slave9"
    ::= { slave9OutputCurrentMax 27}
	
slave9OutputCurrentMaxTwentyeight OBJECT-TYPE
    SYNTAX      DisplayString
    MAX-ACCESS  read-write
    STATUS      current
    DESCRIPTION
	"The second output Max. current alarm value of slave9"
    ::= { slave9OutputCurrentMax 28}	
slave9OutputCurrentMaxTwentynine OBJECT-TYPE
    SYNTAX      DisplayString
    MAX-ACCESS  read-write
    STATUS      current
    DESCRIPTION
	"The second output Max. current alarm value of slave9"
    ::= { slave9OutputCurrentMax 29}
	
slave9OutputCurrentMaxThirty OBJECT-TYPE
    SYNTAX      DisplayString
    MAX-ACCESS  read-write
    STATUS      current
    DESCRIPTION
	"The second output Max. current alarm value of slave9"
    ::= { slave9OutputCurrentMax 30}
	
slave9OutputCurrentMaxThirtyone OBJECT-TYPE
    SYNTAX      DisplayString
    MAX-ACCESS  read-write
    STATUS      current
    DESCRIPTION
	"The second output Max. current alarm value of slave9"
    ::= { slave9OutputCurrentMax 31}
	
slave9OutputCurrentMaxThirtytwo OBJECT-TYPE
    SYNTAX      DisplayString
    MAX-ACCESS  read-write
    STATUS      current
    DESCRIPTION
	"The second output Max. current alarm value of slave9"
    ::= { slave9OutputCurrentMax 32}
	
slave9OutputCurrentMaxThirtythree OBJECT-TYPE
    SYNTAX      DisplayString
    MAX-ACCESS  read-write
    STATUS      current
    DESCRIPTION
	"The second output Max. current alarm value of slave9"
    ::= { slave9OutputCurrentMax 33}
	
slave9OutputCurrentMaxThirtyfour OBJECT-TYPE
    SYNTAX      DisplayString
    MAX-ACCESS  read-write
    STATUS      current
    DESCRIPTION
	"The second output Max. current alarm value of slave9"
    ::= { slave9OutputCurrentMax 34}
	
slave9OutputCurrentMaxThirtyfive OBJECT-TYPE
    SYNTAX      DisplayString
    MAX-ACCESS  read-write
    STATUS      current
    DESCRIPTION
	"The second output Max. current alarm value of slave9"
    ::= { slave9OutputCurrentMax 35}
	
slave9OutputCurrentMaxThirtysix OBJECT-TYPE
    SYNTAX      DisplayString
    MAX-ACCESS  read-write
    STATUS      current
    DESCRIPTION
	"The second output Max. current alarm value of slave9"
    ::= { slave9OutputCurrentMax 36}
	
slave9OutputCurrentMaxThirtyseven OBJECT-TYPE
    SYNTAX      DisplayString
    MAX-ACCESS  read-write
    STATUS      current
    DESCRIPTION
	"The second output Max. current alarm value of slave9"
    ::= { slave9OutputCurrentMax 37}
	
slave9OutputCurrentMaxThirtyeight OBJECT-TYPE
    SYNTAX      DisplayString
    MAX-ACCESS  read-write
    STATUS      current
    DESCRIPTION
	"The second output Max. current alarm value of slave9"
    ::= { slave9OutputCurrentMax 38}
	
slave9OutputCurrentMaxThirtynine OBJECT-TYPE
    SYNTAX      DisplayString
    MAX-ACCESS  read-write
    STATUS      current
    DESCRIPTION
	"The second output Max. current alarm value of slave9"
    ::= { slave9OutputCurrentMax 39}
	
slave9OutputCurrentMaxFourty OBJECT-TYPE
    SYNTAX      DisplayString
    MAX-ACCESS  read-write
    STATUS      current
    DESCRIPTION
	"The second output Max. current alarm value of slave9"
    ::= { slave9OutputCurrentMax 40}
	
slave9OutputCurrentMaxFourtyone OBJECT-TYPE
    SYNTAX      DisplayString
    MAX-ACCESS  read-write
    STATUS      current
    DESCRIPTION
	"The second output Max. current alarm value of slave9"
    ::= { slave9OutputCurrentMax 41}
	
slave9OutputCurrentMaxFourtytwo OBJECT-TYPE
    SYNTAX      DisplayString
    MAX-ACCESS  read-write
    STATUS      current
    DESCRIPTION
	"The second output Max. current alarm value of slave9"
    ::= { slave9OutputCurrentMax 42}
	
	
-------------------------------slave9 output powerfactor------------------------	
slave9OutputPowerfactor OBJECT IDENTIFIER ::= { slave9 9}	

slave9OutputPowerfactorOne OBJECT-TYPE
    SYNTAX      DisplayString
    MAX-ACCESS  read-only
    STATUS      current
    DESCRIPTION
	"The ouput power factor of slave9." 
	::= { slave9OutputPowerfactor 1}

slave9OutputPowerfactorTwo OBJECT-TYPE
    SYNTAX      DisplayString
    MAX-ACCESS  read-only
    STATUS      current
    DESCRIPTION
	"The ouput power factor of slave9." 
	::= { slave9OutputPowerfactor 2}
	
slave9OutputPowerfactorThree OBJECT-TYPE
    SYNTAX      DisplayString
    MAX-ACCESS  read-only
    STATUS      current
    DESCRIPTION
	"The ouput power factor of slave9." 
	::= { slave9OutputPowerfactor 3}
	
slave9OutputPowerfactorFour OBJECT-TYPE
    SYNTAX      DisplayString
    MAX-ACCESS  read-only
    STATUS      current
    DESCRIPTION
	"The ouput power factor of slave9." 
	::= { slave9OutputPowerfactor 4}
		
slave9OutputPowerfactorFive OBJECT-TYPE
    SYNTAX      DisplayString
    MAX-ACCESS  read-only
    STATUS      current
    DESCRIPTION
	"The ouput power factor of slave9." 
	::= { slave9OutputPowerfactor 5}
	
slave9OutputPowerfactorSix OBJECT-TYPE
    SYNTAX      DisplayString
    MAX-ACCESS  read-only
    STATUS      current
    DESCRIPTION
	"The ouput power factor of slave9." 
	::= { slave9OutputPowerfactor 6}
	
slave9OutputPowerfactorSeven OBJECT-TYPE
    SYNTAX      DisplayString
    MAX-ACCESS  read-only
    STATUS      current
    DESCRIPTION
	"The ouput power factor of slave9." 
	::= { slave9OutputPowerfactor 7}	
	
slave9OutputPowerfactorEight OBJECT-TYPE
    SYNTAX      DisplayString
    MAX-ACCESS  read-only
    STATUS      current
    DESCRIPTION
	"The ouput power factor of slave9." 
	::= { slave9OutputPowerfactor 8}
	
slave9OutputPowerfactorNine OBJECT-TYPE
    SYNTAX      DisplayString
    MAX-ACCESS  read-only
    STATUS      current
    DESCRIPTION
	"The ouput power factor of slave9." 
	::= { slave9OutputPowerfactor 9}
		
slave9OutputPowerfactorTen OBJECT-TYPE
    SYNTAX      DisplayString
    MAX-ACCESS  read-only
    STATUS      current
    DESCRIPTION
	"The ouput power factor of slave9." 
	::= { slave9OutputPowerfactor 10}
		
slave9OutputPowerfactorEleven OBJECT-TYPE
    SYNTAX      DisplayString
    MAX-ACCESS  read-only
    STATUS      current
    DESCRIPTION
	"The ouput power factor of slave9." 
	::= { slave9OutputPowerfactor 11}
		
slave9OutputPowerfactorTwel OBJECT-TYPE
    SYNTAX      DisplayString
    MAX-ACCESS  read-only
    STATUS      current
    DESCRIPTION
	"The ouput power factor of slave9." 
	::= { slave9OutputPowerfactor 12}
		
slave9OutputPowerfactorThirteen OBJECT-TYPE
    SYNTAX      DisplayString
    MAX-ACCESS  read-only
    STATUS      current
    DESCRIPTION
	"The ouput power factor of slave9." 
	::= { slave9OutputPowerfactor 13}
		
slave9OutputPowerfactorFourteen OBJECT-TYPE
    SYNTAX      DisplayString
    MAX-ACCESS  read-only
    STATUS      current
    DESCRIPTION
	"The ouput power factor of slave9." 
	::= { slave9OutputPowerfactor 14}
		
slave9OutputPowerfactorFifteen OBJECT-TYPE
    SYNTAX      DisplayString
    MAX-ACCESS  read-only
    STATUS      current
    DESCRIPTION
	"The ouput power factor of slave9." 
	::= { slave9OutputPowerfactor 15}
		
slave9OutputPowerfactorSixteen OBJECT-TYPE
    SYNTAX      DisplayString
    MAX-ACCESS  read-only
    STATUS      current
    DESCRIPTION
	"The ouput power factor of slave9." 
	::= { slave9OutputPowerfactor 16}
		
slave9OutputPowerfactorSeventeen OBJECT-TYPE
    SYNTAX      DisplayString
    MAX-ACCESS  read-only
    STATUS      current
    DESCRIPTION
	"The ouput power factor of slave9." 
	::= { slave9OutputPowerfactor 17}
		
slave9OutputPowerfactorEighteen OBJECT-TYPE
    SYNTAX      DisplayString
    MAX-ACCESS  read-only
    STATUS      current
    DESCRIPTION
	"The ouput power factor of slave9." 
	::= { slave9OutputPowerfactor 18}
		
slave9OutputPowerfactorNineteen OBJECT-TYPE
    SYNTAX      DisplayString
    MAX-ACCESS  read-only
    STATUS      current
    DESCRIPTION
	"The ouput power factor of slave9." 
	::= { slave9OutputPowerfactor 19}
		
slave9OutputPowerfactorTwenty OBJECT-TYPE
    SYNTAX      DisplayString
    MAX-ACCESS  read-only
    STATUS      current
    DESCRIPTION
	"The ouput power factor of slave9." 
	::= { slave9OutputPowerfactor 20}
		
slave9OutputPowerfactorTwentyone OBJECT-TYPE
    SYNTAX      DisplayString
    MAX-ACCESS  read-only
    STATUS      current
    DESCRIPTION
	"The ouput power factor of slave9." 
	::= { slave9OutputPowerfactor 21}
		
slave9OutputPowerfactorTwentytwo OBJECT-TYPE
    SYNTAX      DisplayString
    MAX-ACCESS  read-only
    STATUS      current
    DESCRIPTION
	"The ouput power factor of slave9." 
	::= { slave9OutputPowerfactor 22}
		
slave9OutputPowerfactorTwentythree OBJECT-TYPE
    SYNTAX      DisplayString
    MAX-ACCESS  read-only
    STATUS      current
    DESCRIPTION
	"The ouput power factor of slave9." 
	::= { slave9OutputPowerfactor 23}
		
slave9OutputPowerfactorTwentyfour OBJECT-TYPE
    SYNTAX      DisplayString
    MAX-ACCESS  read-only
    STATUS      current
    DESCRIPTION
	"The ouput power factor of slave9." 
	::= { slave9OutputPowerfactor 24}
		
slave9OutputPowerfactorTwentyfive OBJECT-TYPE
    SYNTAX      DisplayString
    MAX-ACCESS  read-only
    STATUS      current
    DESCRIPTION
	"The ouput power factor of slave9." 
	::= { slave9OutputPowerfactor 25}
		
slave9OutputPowerfactorTwentysix OBJECT-TYPE
    SYNTAX      DisplayString
    MAX-ACCESS  read-only
    STATUS      current
    DESCRIPTION
	"The ouput power factor of slave9." 
	::= { slave9OutputPowerfactor 26}
		
slave9OutputPowerfactorTwentyseven OBJECT-TYPE
    SYNTAX      DisplayString
    MAX-ACCESS  read-only
    STATUS      current
    DESCRIPTION
	"The ouput power factor of slave9." 
	::= { slave9OutputPowerfactor 27}
		
slave9OutputPowerfactorTwentyeight OBJECT-TYPE
    SYNTAX      DisplayString
    MAX-ACCESS  read-only
    STATUS      current
    DESCRIPTION
	"The ouput power factor of slave9." 
	::= { slave9OutputPowerfactor 28}
		
slave9OutputPowerfactorTwentynine OBJECT-TYPE
    SYNTAX      DisplayString
    MAX-ACCESS  read-only
    STATUS      current
    DESCRIPTION
	"The ouput power factor of slave9." 
	::= { slave9OutputPowerfactor 29}
		
slave9OutputPowerfactorThirty OBJECT-TYPE
    SYNTAX      DisplayString
    MAX-ACCESS  read-only
    STATUS      current
    DESCRIPTION
	"The ouput power factor of slave9." 
	::= { slave9OutputPowerfactor 30}
		
slave9OutputPowerfactorThirtyone OBJECT-TYPE
    SYNTAX      DisplayString
    MAX-ACCESS  read-only
    STATUS      current
    DESCRIPTION
	"The ouput power factor of slave9." 
	::= { slave9OutputPowerfactor 31}
		
slave9OutputPowerfactorThirtytwo OBJECT-TYPE
    SYNTAX      DisplayString
    MAX-ACCESS  read-only
    STATUS      current
    DESCRIPTION
	"The ouput power factor of slave9." 
	::= { slave9OutputPowerfactor 32}
		
slave9OutputPowerfactorThirtythree OBJECT-TYPE
    SYNTAX      DisplayString
    MAX-ACCESS  read-only
    STATUS      current
    DESCRIPTION
	"The ouput power factor of slave9." 
	::= { slave9OutputPowerfactor 33}	
	
slave9OutputPowerfactorThirtyfour OBJECT-TYPE
    SYNTAX      DisplayString
    MAX-ACCESS  read-only
    STATUS      current
    DESCRIPTION
	"The ouput power factor of slave9." 
	::= { slave9OutputPowerfactor 34}
	
	
slave9OutputPowerfactorThirtyfive OBJECT-TYPE
    SYNTAX      DisplayString
    MAX-ACCESS  read-only
    STATUS      current
    DESCRIPTION
	"The ouput power factor of slave9." 
	::= { slave9OutputPowerfactor 35}
		
slave9OutputPowerfactorThirtysix OBJECT-TYPE
    SYNTAX      DisplayString
    MAX-ACCESS  read-only
    STATUS      current
    DESCRIPTION
	"The ouput power factor of slave9." 
	::= { slave9OutputPowerfactor 36}
		
slave9OutputPowerfactorThirtyseven OBJECT-TYPE
    SYNTAX      DisplayString
    MAX-ACCESS  read-only
    STATUS      current
    DESCRIPTION
	"The ouput power factor of slave9." 
	::= { slave9OutputPowerfactor 37}
		
slave9OutputPowerfactorThirtyeight OBJECT-TYPE
    SYNTAX      DisplayString
    MAX-ACCESS  read-only
    STATUS      current
    DESCRIPTION
	"The ouput power factor of slave9." 
	::= { slave9OutputPowerfactor 38}
		
slave9OutputPowerfactorThirtynine OBJECT-TYPE
    SYNTAX      DisplayString
    MAX-ACCESS  read-only
    STATUS      current
    DESCRIPTION
	"The ouput power factor of slave9." 
	::= { slave9OutputPowerfactor 39}
		
slave9OutputPowerfactorFourty OBJECT-TYPE
    SYNTAX      DisplayString
    MAX-ACCESS  read-only
    STATUS      current
    DESCRIPTION
	"The ouput power factor of slave9." 
	::= { slave9OutputPowerfactor 40}
		
slave9OutputPowerfactorFourtyone OBJECT-TYPE
    SYNTAX      DisplayString
    MAX-ACCESS  read-only
    STATUS      current
    DESCRIPTION
	"The ouput power factor of slave9." 
	::= { slave9OutputPowerfactor 41}
		
slave9OutputPowerfactorFourtytwo OBJECT-TYPE
    SYNTAX      DisplayString
    MAX-ACCESS  read-only
    STATUS      current
    DESCRIPTION
	"The ouput power factor of slave9." 
	::= { slave9OutputPowerfactor 42}	
	
-------------------------------slave9 output energy------------------------	
slave9OutputEnergy OBJECT IDENTIFIER ::= { slave9 10}

slave9OutputEnergyOne OBJECT-TYPE
    SYNTAX      DisplayString
    MAX-ACCESS  read-only
    STATUS      current
    DESCRIPTION
	"The ouput power of slave9." 
	::= { slave9OutputEnergy 1}

slave9OutputEnergyTwo OBJECT-TYPE
    SYNTAX      DisplayString
    MAX-ACCESS  read-only
    STATUS      current
    DESCRIPTION
	"The ouput power of slave9." 
	::= { slave9OutputEnergy 2}
	
slave9OutputEnergyThree OBJECT-TYPE
    SYNTAX      DisplayString
    MAX-ACCESS  read-only
    STATUS      current
    DESCRIPTION
	"The ouput power of slave9." 
	::= { slave9OutputEnergy 3}
	
slave9OutputEnergyFour OBJECT-TYPE
    SYNTAX      DisplayString
    MAX-ACCESS  read-only
    STATUS      current
    DESCRIPTION
	"The ouput power of slave9." 
	::= { slave9OutputEnergy 4}
		
slave9OutputEnergyFive OBJECT-TYPE
    SYNTAX      DisplayString
    MAX-ACCESS  read-only
    STATUS      current
    DESCRIPTION
	"The ouput power of slave9." 
	::= { slave9OutputEnergy 5}
	
slave9OutputEnergySix OBJECT-TYPE
    SYNTAX      DisplayString
    MAX-ACCESS  read-only
    STATUS      current
    DESCRIPTION
	"The ouput power of slave9." 
	::= { slave9OutputEnergy 6}
	
slave9OutputEnergySeven OBJECT-TYPE
    SYNTAX      DisplayString
    MAX-ACCESS  read-only
    STATUS      current
    DESCRIPTION
	"The ouput power of slave9." 
	::= { slave9OutputEnergy 7}	
	
slave9OutputEnergyEight OBJECT-TYPE
    SYNTAX      DisplayString
    MAX-ACCESS  read-only
    STATUS      current
    DESCRIPTION
	"The ouput power of slave9." 
	::= { slave9OutputEnergy 8}
	
slave9OutputEnergyNine OBJECT-TYPE
    SYNTAX      DisplayString
    MAX-ACCESS  read-only
    STATUS      current
    DESCRIPTION
	"The ouput power of slave9." 
	::= { slave9OutputEnergy 9}
		
slave9OutputEnergyTen OBJECT-TYPE
    SYNTAX      DisplayString
    MAX-ACCESS  read-only
    STATUS      current
    DESCRIPTION
	"The ouput power of slave9." 
	::= { slave9OutputEnergy 10}
		
slave9OutputEnergyEleven OBJECT-TYPE
    SYNTAX      DisplayString
    MAX-ACCESS  read-only
    STATUS      current
    DESCRIPTION
	"The ouput power of slave9." 
	::= { slave9OutputEnergy 11}
		
slave9OutputEnergyTwel OBJECT-TYPE
    SYNTAX      DisplayString
    MAX-ACCESS  read-only
    STATUS      current
    DESCRIPTION
	"The ouput power of slave9." 
	::= { slave9OutputEnergy 12}
		
slave9OutputEnergyThirteen OBJECT-TYPE
    SYNTAX      DisplayString
    MAX-ACCESS  read-only
    STATUS      current
    DESCRIPTION
	"The ouput power of slave9." 
	::= { slave9OutputEnergy 13}
		
slave9OutputEnergyFourteen OBJECT-TYPE
    SYNTAX      DisplayString
    MAX-ACCESS  read-only
    STATUS      current
    DESCRIPTION
	"The ouput power of slave9." 
	::= { slave9OutputEnergy 14}
		
slave9OutputEnergyFifteen OBJECT-TYPE
    SYNTAX      DisplayString
    MAX-ACCESS  read-only
    STATUS      current
    DESCRIPTION
	"The ouput power of slave9." 
	::= { slave9OutputEnergy 15}
		
slave9OutputEnergySixteen OBJECT-TYPE
    SYNTAX      DisplayString
    MAX-ACCESS  read-only
    STATUS      current
    DESCRIPTION
	"The ouput power of slave9." 
	::= { slave9OutputEnergy 16}
		
slave9OutputEnergySeventeen OBJECT-TYPE
    SYNTAX      DisplayString
    MAX-ACCESS  read-only
    STATUS      current
    DESCRIPTION
	"The ouput power of slave9." 
	::= { slave9OutputEnergy 17}
		
slave9OutputEnergyEighteen OBJECT-TYPE
    SYNTAX      DisplayString
    MAX-ACCESS  read-only
    STATUS      current
    DESCRIPTION
	"The ouput power of slave9." 
	::= { slave9OutputEnergy 18}
		
slave9OutputEnergyNineteen OBJECT-TYPE
    SYNTAX      DisplayString
    MAX-ACCESS  read-only
    STATUS      current
    DESCRIPTION
	"The ouput power of slave9." 
	::= { slave9OutputEnergy 19}
		
slave9OutputEnergyTwenty OBJECT-TYPE
    SYNTAX      DisplayString
    MAX-ACCESS  read-only
    STATUS      current
    DESCRIPTION
	"The ouput power of slave9." 
	::= { slave9OutputEnergy 20}
		
slave9OutputEnergyTwentyone OBJECT-TYPE
    SYNTAX      DisplayString
    MAX-ACCESS  read-only
    STATUS      current
    DESCRIPTION
	"The ouput power of slave9." 
	::= { slave9OutputEnergy 21}
		
slave9OutputEnergyTwentytwo OBJECT-TYPE
    SYNTAX      DisplayString
    MAX-ACCESS  read-only
    STATUS      current
    DESCRIPTION
	"The ouput power of slave9." 
	::= { slave9OutputEnergy 22}
		
slave9OutputEnergyTwentythree OBJECT-TYPE
    SYNTAX      DisplayString
    MAX-ACCESS  read-only
    STATUS      current
    DESCRIPTION
	"The ouput power of slave9." 
	::= { slave9OutputEnergy 23}
		
slave9OutputEnergyTwentyfour OBJECT-TYPE
    SYNTAX      DisplayString
    MAX-ACCESS  read-only
    STATUS      current
    DESCRIPTION
	"The ouput power of slave9." 
	::= { slave9OutputEnergy 24}
		
slave9OutputEnergyTwentyfive OBJECT-TYPE
    SYNTAX      DisplayString
    MAX-ACCESS  read-only
    STATUS      current
    DESCRIPTION
	"The ouput power of slave9." 
	::= { slave9OutputEnergy 25}
		
slave9OutputEnergyTwentysix OBJECT-TYPE
    SYNTAX      DisplayString
    MAX-ACCESS  read-only
    STATUS      current
    DESCRIPTION
	"The ouput power of slave9." 
	::= { slave9OutputEnergy 26}
		
slave9OutputEnergyTwentyseven OBJECT-TYPE
    SYNTAX      DisplayString
    MAX-ACCESS  read-only
    STATUS      current
    DESCRIPTION
	"The ouput power of slave9." 
	::= { slave9OutputEnergy 27}
		
slave9OutputEnergyTwentyeight OBJECT-TYPE
    SYNTAX      DisplayString
    MAX-ACCESS  read-only
    STATUS      current
    DESCRIPTION
	"The ouput power of slave9." 
	::= { slave9OutputEnergy 28}
		
slave9OutputEnergyTwentynine OBJECT-TYPE
    SYNTAX      DisplayString
    MAX-ACCESS  read-only
    STATUS      current
    DESCRIPTION
	"The ouput power of slave9." 
	::= { slave9OutputEnergy 29}
		
slave9OutputEnergyThirty OBJECT-TYPE
    SYNTAX      DisplayString
    MAX-ACCESS  read-only
    STATUS      current
    DESCRIPTION
	"The ouput power of slave9." 
	::= { slave9OutputEnergy 30}
		
slave9OutputEnergyThirtyone OBJECT-TYPE
    SYNTAX      DisplayString
    MAX-ACCESS  read-only
    STATUS      current
    DESCRIPTION
	"The ouput power of slave9." 
	::= { slave9OutputEnergy 31}
		
slave9OutputEnergyThirtytwo OBJECT-TYPE
    SYNTAX      DisplayString
    MAX-ACCESS  read-only
    STATUS      current
    DESCRIPTION
	"The ouput power of slave9." 
	::= { slave9OutputEnergy 32}
		
slave9OutputEnergyThirtythree OBJECT-TYPE
    SYNTAX      DisplayString
    MAX-ACCESS  read-only
    STATUS      current
    DESCRIPTION
	"The ouput power of slave9." 
	::= { slave9OutputEnergy 33}	
	
slave9OutputEnergyThirtyfour OBJECT-TYPE
    SYNTAX      DisplayString
    MAX-ACCESS  read-only
    STATUS      current
    DESCRIPTION
	"The ouput power of slave9." 
	::= { slave9OutputEnergy 34}
	
	
slave9OutputEnergyThirtyfive OBJECT-TYPE
    SYNTAX      DisplayString
    MAX-ACCESS  read-only
    STATUS      current
    DESCRIPTION
	"The ouput power of slave9." 
	::= { slave9OutputEnergy 35}
		
slave9OutputEnergyThirtysix OBJECT-TYPE
    SYNTAX      DisplayString
    MAX-ACCESS  read-only
    STATUS      current
    DESCRIPTION
	"The ouput power of slave9." 
	::= { slave9OutputEnergy 36}
		
slave9OutputEnergyThirtyseven OBJECT-TYPE
    SYNTAX      DisplayString
    MAX-ACCESS  read-only
    STATUS      current
    DESCRIPTION
	"The ouput power of slave9." 
	::= { slave9OutputEnergy 37}
		
slave9OutputEnergyThirtyeight OBJECT-TYPE
    SYNTAX      DisplayString
    MAX-ACCESS  read-only
    STATUS      current
    DESCRIPTION
	"The ouput power of slave9." 
	::= { slave9OutputEnergy 38}
		
slave9OutputEnergyThirtynine OBJECT-TYPE
    SYNTAX      DisplayString
    MAX-ACCESS  read-only
    STATUS      current
    DESCRIPTION
	"The ouput power of slave9." 
	::= { slave9OutputEnergy 39}
		
slave9OutputEnergyFourty OBJECT-TYPE
    SYNTAX      DisplayString
    MAX-ACCESS  read-only
    STATUS      current
    DESCRIPTION
	"The ouput power of slave9." 
	::= { slave9OutputEnergy 40}
		
slave9OutputEnergyFourtyone OBJECT-TYPE
    SYNTAX      DisplayString
    MAX-ACCESS  read-only
    STATUS      current
    DESCRIPTION
	"The ouput power of slave9." 
	::= { slave9OutputEnergy 41}
		
slave9OutputEnergyFourtytwo OBJECT-TYPE
    SYNTAX      DisplayString
    MAX-ACCESS  read-only
    STATUS      current
    DESCRIPTION
	"The ouput power of slave9." 
	::= { slave9OutputEnergy 42}	
	
	
		
	
-------------------------------End ---------------------------------------------     
                                                                                     
                                                                                     
END
